submodule Cisco-IOS-XR-man-ems-oper-sub1 {

  belongs-to Cisco-IOS-XR-man-ems-oper {
    prefix Cisco-IOS-XR-man-ems-oper;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR man-ems package operational data.

     Copyright (c) 2013-2018 by Cisco Systems, Inc.
     All rights reserved.";

  revision "2015-11-09" {
    description
      "IOS XR 6.0 revision.";
  }


  grouping GRPC-STATUS-INFO-B {
    description "gRPC status";
    leaf transport {
      type string;
      description "GRPCTransport";
    }
    leaf address-family {
      type string;
      description "AddressFamily";
    }
    leaf tls {
      type string;
      description "GRPCTLS";
    }
    leaf trustpoint {
      type string;
      description "GRPCTrustpoint";
    }
    leaf listening-port {
      type int32;
      description "ListeningPort";
    }
    leaf vrf-socket-ns-path {
      type string;
      description "VrfSocketNamespacePath";
    }
    leaf max-req-per-user {
      type uint32;
      description "MaxReqPerUser";
    }
    leaf max-req-total {
      type uint32;
      description "MaxReqTotal";
    }
    leaf max-streams {
      type uint32;
      description "Maximum number of streaming gRPCs";
    }
    leaf max-streams-per-user {
      type uint32;
      description "Maximum number of streaming gRPCs per user";
    }
  }

  grouping GRPC-STATISTICS-INFO-B {
    description "gRPC statistics";
    leaf ct-show-cmd-txt-req-recv {
      type uint64;
      description "CounterShowCmdTxtReqRecv";
    }
    leaf ct-show-cmd-txt-res-sent {
      type uint64;
      description "CounterShowCmdTxtResSent";
    }
    leaf ct-get-config-req-recv {
      type uint64;
      description "CounterGetConfigReqRecv";
    }
    leaf ct-get-config-res-sent {
      type uint64;
      description "CounterGetConfigResSent";
    }
    leaf ct-cli-config-req-recv {
      type uint64;
      description "CounterCliConfigReqRecv";
    }
    leaf ct-cli-config-res-sent {
      type uint64;
      description "CounterCliConfigResSent";
    }
    leaf ct-merge-config-req-recv {
      type uint64;
      description "CounterMergeConfigReq";
    }
    leaf ct-merge-config-res-sent {
      type uint64;
      description "CounterMergeConfigRes";
    }
    leaf ct-commit-replace-req-recv {
      type uint64;
      description "CounterCommitReplaceReq";
    }
    leaf ct-commit-replace-res-sent {
      type uint64;
      description "CounterCommitReplaceRes";
    }
    leaf ct-delete-config-req-recv {
      type uint64;
      description "CounterDeleteConfigReq";
    }
    leaf ct-delete-config-res-sent {
      type uint64;
      description "CounterDeleteConfigRes";
    }
    leaf ct-replace-config-req-recv {
      type uint64;
      description "CounterReplaceConfigReq";
    }
    leaf ct-replace-config-res-sent {
      type uint64;
      description "CounterReplaceConfigSent";
    }
    leaf ct-get-oper-req-recv {
      type uint64;
      description "CounterGetOperReqRecv";
    }
    leaf ct-get-oper-res-sent {
      type uint64;
      description "CounterGetOperResSent";
    }
    leaf ct-get-current-session {
      type uint32;
      description "CounterGetCurrentSession";
    }
    leaf ct-commit-config-req-recv {
      type uint64;
      description "CounterForHowManyCommitConfigRequests";
    }
    leaf ct-commit-config-res-sent {
      type uint64;
      description "CounterForHowManyCommitConfigResponses";
    }
    leaf ct-action-json-req-recv {
      type uint64;
      description "CounterForHowManyActionJsonRequests";
    }
    leaf ct-action-json-res-sent {
      type uint64;
      description "CounterForHowManyActionJsonResponses";
    }
  }
}
