module Cisco-IOS-XR-wanphy-ui-cfg {

  /*** NAMESPACE / PREFIX DEFINITION ***/

  namespace "http://cisco.com/ns/yang/Cisco-IOS-XR-wanphy-ui-cfg";


  prefix "wanphy-ui-cfg";

  /*** LINKAGE (IMPORTS / INCLUDES) ***/

  import Cisco-IOS-XR-ifmgr-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR wanphy-ui package configuration.

     This YANG module augments the
       Cisco-IOS-XR-ifmgr-cfg
     module with configuration data.

     Copyright (c) 2013-2018 by Cisco Systems, Inc.
     All rights reserved.";

  revision "2015-11-09" {
    description
      "IOS XR 6.0 revision.";
  }

  typedef Wanphy-lan-mode {
    type enumeration {
      enum on {
        value 1;
        description "LanMode";
      }
    }
    description "Wanphy lan mode";
  }
  typedef Wanphy-wan-mode {
    type enumeration {
      enum on {
        value 1;
        description "WAN Mode";
      }
    }
    description "Wanphy wan mode";
  }

  augment "/a1:interface-configurations/a1:interface-configuration" {

    container wanphy {
      description "WANPHY port controller configuration";
      leaf report-path-rdi {
        type empty;
        description
          "Configure Path Remote Defect Indicator
          reporting";
      }
      leaf report-los {
        type empty;
        description "Configure Loss Of Signal reporting";
      }
      leaf report-path-lcd {
        type empty;
        description
          "Configure Path Loss Of Code-Group Delineation
          reporting";
      }
      leaf report-path-fe-plm {
        type empty;
        description
          "Configure Path Far End Payload Label Mismatch
          reporting";
      }
      leaf lan-mode {
        type Wanphy-lan-mode;
        description "Configure LAN Mode";
      }
      leaf report-path-plm {
        type empty;
        description
          "Configure Path Payload Label Mismatch reporting";
      }
      leaf report-path-fe-ais {
        type empty;
        description
          "Configure Path Far End Payload Label Mismatch
          reporting";
      }
      leaf report-path-ais {
        type empty;
        description
          "Configure Path Alarm Indication Signal
          reporting";
      }
      leaf report-line-ais {
        type empty;
        description
          "Configure Line Alarm Indication Signal
          reporting";
      }
      leaf report-lof {
        type empty;
        description "Configure Loss Of Frame reporting";
      }
      leaf report-lop {
        type empty;
        description "Configure Loss Of Pointer reporting";
      }
      leaf report-rdi {
        type empty;
        description "Configure Remote Defect Indicator reporting";
      }
      leaf report-sd-ber {
        type empty;
        description
          "Configure B2 BER in excess of SD threshold
          reporting";
      }
      leaf threshold-sd-ber {
        type uint32 {
          range "3..9";
        }
        default "6";
        description
          "Bit error rate is 10 to the minus n, where n is
          threshold value";
      }
      leaf report-sf-ber {
        type empty;
        description
          "Configure B2 BER in excess of SF threshold
          reporting";
      }
      leaf threshold-sf-ber {
        type uint32 {
          range "3..9";
        }
        default "3";
        description
          "Bit error rate is 10 to the minus n, where n is
          threshold value";
      }
      leaf wan-mode {
        type Wanphy-wan-mode;
        description "Configure WAN Mode";
      }
    }
    description
      "This augment extends the configuration data of
      'Cisco-IOS-XR-ifmgr-cfg'";
  }
}
