submodule Cisco-IOS-XR-PRIVATE-ocni-mpls-te-oper-sub1 {

  belongs-to Cisco-IOS-XR-PRIVATE-ocni-mpls-te-oper {
    prefix Cisco-IOS-XR-PRIVATE-ocni-mpls-te-oper;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR PRIVATE-ocni-mpls-te package operational data.

     Copyright (c) 2013-2018 by Cisco Systems, Inc.
     All rights reserved.";

  revision "2015-11-09" {
    description
      "IOS XR 6.0 revision.";
  }

  typedef Openconfig-mpls-threshold-specification-enum {
    type enumeration {
      enum mirrored-up-down {
        value 0;
        description
          "MIRRORED_UP_DOWN indicates that a single set of
          threshold values should be used for both
          increasing and decreasing bandwidth when
          determining whether to trigger updated
          bandwidth values to be flooded in the IGP TE
          extensions.";
      }
      enum separate-up-down {
        value 1;
        description
          "SEPARATE_UP_DOWN indicates that a separate
          threshold values should be used for the
          increasing and decreasing bandwidth when
          determining whether to trigger updated
          bandwidth values to be flooded in the IGP TE
          extensions.";
      }
    }
    description "Openconfig mpls threshold specification enum";
  }
  typedef Openconfig-mpls-threshold-type-enum {
    type enumeration {
      enum delta {
        value 0;
        description
          "DELTA indicates that the local system should
          flood IGP updates when a change in reserved
          bandwidth >= the specified delta occurs on the
          interface.";
      }
      enum threshold-crossed {
        value 1;
        description
          "THRESHOLD-CROSSED indicates that the local
          system should trigger an update (and hence
          flood) the reserved bandwidth when the reserved
          bandwidth changes such that it crosses, or
          becomes equal to one of the threshold values.";
      }
    }
    description "Openconfig mpls threshold type enum";
  }
  typedef Openconfig-mpls-te-mpls-srlg-flooding-type-enum {
    type enumeration {
      enum flooded-srlg {
        value 0;
        description "SRLG is flooded in the IGP";
      }
      enum static-srlg {
        value 1;
        description
          "SRLG is not flooded, the members are statically
          configured";
      }
    }
    description "Openconfig mpls te mpls srlg flooding type enum";
  }
  typedef Openconfig-rsvp-sr-ext-update-trigger-enum {
    type enumeration {
      enum adjusted-max-reservable-pct {
        value 0;
        description
          "Update of a new maximum reservable bandwidth
          IGP TLV is based on the value changing >= X% of
          the currently flooded
          adjusted-absolute-subscription-bw. The
          percentage of this value that is used is
          specified by the adjusted-max-reservable-bw-pct
          leaf.";
      }
      enum sr-traffic-pct {
        value 1;
        description
          "Update of the new maximum reservable bandwidth
          IGP TLV is based on the value changing >= X% of
          the last calculated segment routing traffic
          utilisation for the interface. The percentage
          delta of this value is specified by the
          sr-traffic-pct leaf.";
      }
    }
    description "Openconfig rsvp sr ext update trigger enum";
  }
  typedef Openconfig-mpls-te-cspf-tie-breaking-enum {
    type enumeration {
      enum random {
        value 0;
        description
          "CSPF calculation selects a random path among
          multiple equal-cost paths to the destination";
      }
      enum least-fill {
        value 1;
        description
          "CSPF calculation selects the path with greatest
          available bandwidth";
      }
      enum most-fill {
        value 2;
        description
          "CSPF calculation selects the path with the
          least available bandwidth";
      }
    }
    description "Openconfig mpls te cspf tie breaking enum";
  }
  typedef Openconfig-mpls-te-te-bandwidth-type-enum {
    type enumeration {
      enum specified {
        value 0;
        description "Bandwidth is explicitly specified";
      }
      enum auto {
        value 1;
        description "Bandwidth is automatically computed";
      }
    }
    description "Openconfig mpls te te bandwidth type enum";
  }
  typedef Openconfig-mpls-te-mpls-hop-type-enum {
    type enumeration {
      enum loose {
        value 0;
        description "loose hop in an explicit path";
      }
      enum strict {
        value 1;
        description "strict hop in an explicit path";
      }
    }
    description "Openconfig mpls te mpls hop type enum";
  }
  typedef Yang2bag-string {
    type string;
    description "Yang2bag string";
  }

  grouping INTERFACE-BANDWIDTH-MEASUREMENT-STATE {
    description "INTERFACE BANDWIDTH MEASUREMENT STATE";
    leaf last-sample-time {
      type uint64;
      description
        "The time at which the last sample of bandwidth
        utilisation for both RSVP-TE and non-RSVP-TE
        traffic was taken";
    }
    leaf last-sample-measured-rsvp-util {
      type uint64;
      description
        "The measured RSVP-TE bandwidth utilisation at
        the last sample (whose time is indicated in
        last-sample-time)";
    }
    leaf last-sample-measured-sr-util {
      type uint64;
      description
        "The measured Segment Routing bandwidth
        utilisation at the last sample (whose time is
        indicated in last-sample-time)";
    }
    leaf last-calculated-time {
      type uint64;
      description
        "The time at which the last calculated value for
        bandwidth utilisation was performed";
    }
    leaf last-calculated-sr-utilisation {
      type uint64;
      description
        "The last calculated value of the Segment Routing
        utilisation (taken post any averaging or
        adjustment that occurs)";
    }
    leaf last-flooded-time {
      type uint64;
      units "nanosecond";
      description
        "The time, expressed in nanoseconds since the
        epoch, at which the bandwidth utilisation of
        non-RSVP-TE traffic resulted in the value being
        flooded in the IGP";
    }
  }

  grouping BANDWIDTH-MEASUREMENT {
    description "BANDWIDTH MEASUREMENT";

    container state {
      description
        "Operational state parameters relating to the
        containing interface's bandwidth measurement";
      uses INTERFACE-BANDWIDTH-MEASUREMENT-STATE;
    }
  }

  grouping IGP-FLOODING-BANDWIDTH-STATE {
    description "IGP FLOODING BANDWIDTH STATE";
    leaf threshold-type {
      type Openconfig-mpls-threshold-type-enum;
      description
        "The type of threshold that should be used to
        specify the values at which bandwidth is flooded";
    }
    leaf delta-percentage {
      type uint8;
      units "percentage";
      description
        "The percentage of the
        maximum-reservable-bandwidth considered as the
        delta that results in an IGP update being
        flooded";
    }
    leaf threshold-specification {
      type Openconfig-mpls-threshold-specification-enum;
      description
        "This value specifies whether a single set of
        threshold values should be used for both
        increasing and decreasing bandwidth when
        determining whether to trigger updated bandwidth
        values to be flooded in the IGP TE extensions";
    }
    leaf-list up-threshold {
      type uint8;
      units "percentage";
      description
        "The thresholds (expressed as a percentage of the
        maximum reservable bandwidth) at which bandwidth
        updates are to be triggered when the bandwidth
        is increasing";
    }
    leaf-list down-threshold {
      type uint8;
      units "percentage";
      description
        "The thresholds (expressed as a percentage of the
        maximum reservable bandwidth) at which bandwidth
        updates are to be triggered when the bandwidth
        is decreasing";
    }
  }

  grouping IGP-FLOODING-BANDWIDTH {
    description "IGP FLOODING BANDWIDTH";

    container state {
      description "State parameters for TED update threshold ";
      uses IGP-FLOODING-BANDWIDTH-STATE;
    }
  }

  grouping INTERFACE-REF-STATE {
    description "INTERFACE REF STATE";
    leaf interface {
      type Yang2bag-string;
      description "Reference to a base interface";
    }
    leaf subinterface {
      type uint32;
      description
        "Reference to a subinterface -- this requires the
        base interface to be specified using the
        interface leaf in this container";
    }
  }

  grouping INTERFACE-REF {
    description "INTERFACE REF";

    container state {
      description "Operational state for interface-ref";
      uses INTERFACE-REF-STATE;
    }
  }

  grouping INTERFACE-STATE {
    description "INTERFACE STATE";
    leaf interface-id {
      type Yang2bag-string;
      description "Id of the interface";
    }
    leaf te-metric {
      type uint32;
      description "TE specific metric for the link";
    }
    leaf-list srlg-membership {
      type Yang2bag-string;
      description
        "list of references to named shared risk link
        groups that the interface belongs to";
    }
    leaf-list admin-group {
      type Yang2bag-string;
      description "list of admin groups (by name) on the interface";
    }
  }

  grouping OVERLAY-OCNI-MPLS-TE-INTERFACE {
    description "List of TE interfaces";

    container state {
      description "State parameters related to TE interfaces";
      uses INTERFACE-STATE;
    }

    container interface-ref {
      description "Reference to an interface or subinterface";
      uses INTERFACE-REF;
    }

    container igp-flooding-bandwidth {
      description
        "Interface bandwidth change percentages that
        trigger update events into the IGP traffic
        engineering database (TED)";
      uses IGP-FLOODING-BANDWIDTH;
    }

    container bandwidth-measurement {
      description
        "Configuration and operational state parameters
        relating to per-interface bandwidth measurement";
      uses BANDWIDTH-MEASUREMENT;
    }
  }

  grouping SUBSCRIPTION-STATE {
    description "SUBSCRIPTION STATE";
    leaf adjusted-absolute-subscription-bw {
      type uint64;
      units "kbit/s";
      description
        "The adjusted absolute value (in kbps) of the
        bandwidth which is reservable to RSVP-TE on the
        local system";
    }
  }

  grouping OVERLAY-OCNI-MPLS-TE-SUBSCRIPTION {
    description
      "Bandwidth percentage reservable by RSVP on an
      interface";

    container state {
      description
        "State parameters relating to RSVP subscription
        options";
      uses SUBSCRIPTION-STATE;
    }
  }

  grouping PROTECTION-STATE {
    description "PROTECTION STATE";
    leaf link-protection-style-requested {
      type Yang2bag-string;
      description
        "Style of mpls frr protection desired: link,
        link-node, or unprotected";
    }
  }

  grouping OVERLAY-OCNI-MPLS-TE-PROTECTION {
    description "link-protection (NHOP) related configuration";

    container state {
      description "State for link-protection";
      uses PROTECTION-STATE;
    }
  }

  grouping INTERFACE-INTERFACE-REF-STATE {
    description "INTERFACE INTERFACE REF STATE";
    leaf interface {
      type Yang2bag-string;
      description "Reference to a base interface";
    }
    leaf subinterface {
      type uint32;
      description
        "Reference to a subinterface -- this requires the
        base interface to be specified using the
        interface leaf in this container";
    }
  }

  grouping OVERLAY-OCNI-MPLS-TE-INTERFACE-REF {
    description "Reference to an interface or subinterface";

    container state {
      description "Operational state for interface-ref";
      uses INTERFACE-INTERFACE-REF-STATE;
    }
  }

  grouping BANDWIDTH-RESERVATION-STATE {
    description "BANDWIDTH RESERVATION STATE";
    leaf priority {
      type Yang2bag-string;
      description
        "RSVP priority level for LSPs traversing the
        interface";
    }
    leaf available-bandwidth {
      type uint64;
      description
        "Bandwidth currently available with the priority
        level, or for the entire interface when the
        priority is set to ALL";
    }
    leaf reserved-bandwidth {
      type uint64;
      description
        "Bandwidth currently reserved within the priority
        level, or the sum of all priority levels when
        the keyword is set to ALL";
    }
    leaf active-reservations-count {
      type uint64;
      description
        "Number of active RSVP reservations in the
        associated priority, or the sum of all
        reservations when the priority level is set to
        ALL";
    }
    leaf highwater-mark {
      type uint64;
      description
        "Maximum bandwidth reserved on the interface
        within the priority, or across all priorities in
        the case that the priority level is set to ALL";
    }
  }

  grouping OVERLAY-OCNI-MPLS-TE-BANDWIDTH-RESERVATION {
    description
      "Available and reserved bandwidth by priority on
      the interface";

    container state {
      description
        "Operational state parameters relating to a
        bandwidth reservation at a certain priority";
      uses BANDWIDTH-RESERVATION-STATE;
    }
  }

  grouping SOFT-PREEMPTION-STATE {
    description "SOFT PREEMPTION STATE";
    leaf enable {
      type boolean;
      description "Enables soft preemption on a node";
    }
    leaf soft-preemption-timeout {
      type uint16;
      description
        "Timeout value for soft preemption to revert to
        hard preemption";
    }
  }

  grouping SOFT-PREEMPTION {
    description "SOFT PREEMPTION";

    container state {
      description
        "State parameters relating to RSVP soft
        preemption support";
      uses SOFT-PREEMPTION-STATE;
    }
  }

  grouping OVERLAY-OCNI-MPLS-TE-RSVP-TE-GLOBAL {
    description "Platform wide RSVP configuration and state";

    container soft-preemption {
      description
        "Protocol options relating to RSVP soft
        preemption";
      uses SOFT-PREEMPTION;
    }
  }

  grouping MEMBERS-LIST-STATE {
    description "MEMBERS LIST STATE";
    leaf from-address {
      type Yang2bag-string;
      description "IP address of the a-side of the SRLG link";
    }
    leaf to-address {
      type Yang2bag-string;
      description "IP address of the z-side of the SRLG link";
    }
  }

  grouping OVERLAY-OCNI-MPLS-TE-MEMBERS-LIST {
    description
      "List of SRLG members, which are expressed as IP
      address endpoints of links contained in the SRLG";

    container state {
      description "State parameters relating to the SRLG members";
      uses MEMBERS-LIST-STATE;
    }
  }

  grouping OVERLAY-OCNI-MPLS-TE-STATE {
    description "State parameters related to the SRLG";
    leaf name {
      type Yang2bag-string;
      description "SRLG group identifier";
    }
    leaf value {
      type uint32;
      description "group ID for the SRLG";
    }
    leaf cost {
      type uint32;
      description
        "The cost of the SRLG to the computation
        algorithm";
    }
    leaf flooding-type {
      type Openconfig-mpls-te-mpls-srlg-flooding-type-enum;
      description
        "The type of SRLG, either flooded in the IGP or
        statically configured";
    }
  }

  grouping TE-LSP-TIMERS-STATE {
    description "TE LSP TIMERS STATE";
    leaf install-delay {
      type uint16;
      description
        "delay the use of newly installed te lsp for a
        specified amount of time";
    }
    leaf cleanup-delay {
      type uint16;
      description
        "delay the removal of old te lsp for a specified
        amount of time";
    }
    leaf reoptimize-timer {
      type uint16;
      description
        "frequency of reoptimization of a traffic
        engineered LSP";
    }
  }

  grouping OVERLAY-OCNI-MPLS-TE-TE-LSP-TIMERS {
    description
      "Definition for delays associated with setup and
      cleanup of TE LSPs";

    container state {
      description "State related to timers for TE LSPs";
      uses TE-LSP-TIMERS-STATE;
    }
  }

  grouping ADMIN-GROUP-STATE {
    description "ADMIN GROUP STATE";
    leaf admin-group-name {
      type Yang2bag-string;
      description "name for mpls admin-group";
    }
    leaf bit-position {
      type uint32;
      description "bit-position value for mpls admin-group";
    }
  }

  grouping OVERLAY-OCNI-MPLS-TE-ADMIN-GROUP {
    description
      "configuration of value to name mapping for mpls
      affinities/admin-groups";

    container state {
      description "Operational state for admin-groups";
      uses ADMIN-GROUP-STATE;
    }
  }

  grouping UPDATE-TRIGGER-STATE {
    description "UPDATE TRIGGER STATE";
    leaf update-trigger {
      type Openconfig-rsvp-sr-ext-update-trigger-enum;
      description
        "The trigger that should be used to determine
        when the IGP TED is updated with new information
        as to the effective maximum reservable bandwidth
        (adjusted-absolute-subscription-bw)";
    }
    leaf adjusted-max-reservable-bw-pct {
      type uint8;
      description
        "The delta in the
        adjusted-max-reservable-bandwidth that should
        trigger an update in the value which is flooded
        through the IGP TED";
    }
  }

  grouping UPDATE-TRIGGER {
    description "UPDATE TRIGGER";

    container state {
      description
        "Operational state parameters related to the
        bandwidth measurement update trigger";
      uses UPDATE-TRIGGER-STATE;
    }
  }

  grouping BANDWIDTH-MEASUREMENT-STATE {
    description "BANDWIDTH MEASUREMENT STATE";
    leaf measure-sr-traffic {
      type boolean;
      description
        "When this leaf is set to true, the local system
        should measure the bandwidth utilisation of SR
        traffic on interfaces for which TED entries are
        being generated";
    }
    leaf collection-interval {
      type uint32;
      description
        "The interval at which the collection of
        interface statistics relating to non-RSVP-TE
        traffic should be performed";
    }
    leaf adjustment-interval {
      type uint32;
      description
        "The interval after which an adjustment to the
        utilised bandwidth on the interface is made";
    }
    leaf bandwidth-multiplier {
      type Yang2bag-string;
      description
        "A multiplier applied to the sampled bandwidth
        which determines the value that is propagated to
        the IGP TED";
    }
    leaf effective-adjustment-interval {
      type uint32;
      description
        "The effective adjustment interval that is being
        used by the system";
    }
  }

  grouping OVERLAY-OCNI-MPLS-TE-BANDWIDTH-MEASUREMENT {
    description
      "Configuration and operational state parameters
      related to how bandwidth utilisation is measured
      and flooded into the IGP";

    container state {
      description
        "Operational state parameters relating to
        bandwidth measurement";
      uses BANDWIDTH-MEASUREMENT-STATE;
    }

    container update-trigger {
      description
        "Configuration and operational state parameters
        related to the update trigger for flooding new
        bandwidth information into the IGP";
      uses UPDATE-TRIGGER;
    }
  }

  grouping OVERLAY-OCNI-MPLS-TE-P2P-TUNNEL-ATTRIBUTES-STATE {
    description "State parameters for P2P LSPs";
    leaf destination {
      type Yang2bag-string;
      description "P2P tunnel destination address";
    }
  }

  grouping ADMIN-GROUPS-STATE {
    description "ADMIN GROUPS STATE";
    leaf-list exclude-group {
      type Yang2bag-string;
      description
        "list of references to named admin-groups to
        exclude in path calculation";
    }
    leaf-list include-any-group {
      type Yang2bag-string;
      description
        "list of references to named admin-groups of
        which one must be included";
    }
  }

  grouping ADMIN-GROUPS {
    description "ADMIN GROUPS";

    container state {
      description "Operational state data ";
      uses ADMIN-GROUPS-STATE;
    }
  }

  grouping P2P-PRIMARY-PATH-STATE {
    description "P2P PRIMARY PATH STATE";
    leaf name {
      type Yang2bag-string;
      description "Path name";
    }
    leaf path-computation-method {
      type Yang2bag-string;
      description
        "The method used for computing the path, either
        locally computed, queried from a server or not
        computed at all (explicitly configured)";
    }
    leaf use-cspf {
      type boolean;
      description "Flag to enable CSPF for locally computed LSPs";
    }
    leaf cspf-tiebreaker {
      type Openconfig-mpls-te-cspf-tie-breaking-enum;
      description
        "Determine the tie-breaking method to choose
        between equally desirable paths during CSFP
        computation";
    }
    leaf explicit-path-name {
      type Yang2bag-string;
      description "reference to a defined path";
    }
    leaf preference {
      type uint8;
      description "Specifies a preference for this path";
    }
    leaf setup-priority {
      type uint8;
      description
        "RSVP-TE preemption priority during LSP setup,
        lower is higher priority; default 7 indicates
        that LSP will not preempt established LSPs
        during setup";
    }
    leaf hold-priority {
      type uint8;
      description
        "preemption priority once the LSP is established,
        lower is higher priority; default 0 indicates
        other LSPs will not preempt the LSPs once
        established";
    }
    leaf associated-rsvp-session {
      type uint64;
      description
        "If the signalling protocol specified for this
        path is RSVP-TE, this leaf provides a reference
        to the associated session within the RSVP-TE
        protocol sessions list, such that details of the
        signaling can be retrieved";
    }
  }

  grouping OVERLAY-OCNI-MPLS-TE-P2P-PRIMARY-PATH {
    description "List of p2p primary paths for a tunnel";

    container state {
      description "State parameters related to paths";
      uses P2P-PRIMARY-PATH-STATE;
    }

    container admin-groups {
      description
        "Top-level container for include/exclude
        constraints for link affinities";
      uses ADMIN-GROUPS;
    }
  }

  grouping COUNTERS {
    description "COUNTERS";
    leaf bytes {
      type uint64;
      units "byte";
      description
        "Number of bytes that have been forwarded over
        the label switched path";
    }
    leaf packets {
      type uint64;
      description
        "Number of pacets that have been forwarded over
        the label switched path";
    }
    leaf path-changes {
      type uint64;
      description
        "Number of path changes for the label switched
        path";
    }
    leaf state-changes {
      type uint64;
      description
        "Number of state changes for the label switched
        path";
    }
    leaf online-time {
      type Yang2bag-string;
      description
        "Indication of the time the label switched path
        transitioned to an Oper Up or in-service state";
    }
    leaf current-path-time {
      type Yang2bag-string;
      description
        "Indicates the time the LSP switched onto its
        current path";
    }
    leaf next-reoptimization-time {
      type Yang2bag-string;
      description
        "Indicates the next scheduled time the LSP will
        be reoptimized";
    }
  }

  grouping OVERLAY-OCNI-MPLS-TE-TUNNEL-STATE {
    description "State parameters related to TE tunnels";

    container counters {
      description "State data for MPLS label switched paths";
      uses COUNTERS;
    }
    leaf name {
      type Yang2bag-string;
      description "The tunnel name";
    }
    leaf type {
      type Yang2bag-string;
      description "Tunnel type, p2p or p2mp";
    }
    leaf signaling-protocol {
      type Yang2bag-string;
      description "Signaling protocol used to set up this tunnel";
    }
    leaf description {
      type Yang2bag-string;
      description "optional text description for the tunnel";
    }
    leaf admin-status {
      type Yang2bag-string;
      description "TE tunnel administrative state";
    }
    leaf metric-type {
      type Yang2bag-string;
      description
        "The type of metric specification that should be
        used to set the LSP(s) metric";
    }
    leaf metric {
      type int32;
      description
        "The value of the metric that should be specified";
    }
    leaf shortcut-eligible {
      type boolean;
      description
        "Whether this LSP is considered to be eligible
        for us as a shortcut in the IGP";
    }
    leaf protection-style-requested {
      type Yang2bag-string;
      description
        "style of mpls frr protection desired: can be
        link, link-node or unprotected";
    }
    leaf reoptimize-timer {
      type uint16;
      description
        "frequency of reoptimization of a traffic
        engineered LSP";
    }
    leaf source {
      type Yang2bag-string;
      description "RSVP-TE tunnel source address";
    }
    leaf soft-preemption {
      type boolean;
      description "Enables RSVP soft-preemption on this LSP";
    }
    leaf setup-priority {
      type uint8;
      description
        "RSVP-TE preemption priority during LSP setup,
        lower is higher priority; default 7 indicates
        that LSP will not preempt established LSPs
        during setup";
    }
    leaf hold-priority {
      type uint8;
      description
        "preemption priority once the LSP is established,
        lower is higher priority; default 0 indicates
        other LSPs will not preempt the LSPs once
        established";
    }
    leaf oper-status {
      type Yang2bag-string;
      description "The operational status of the TE tunnel";
    }
    leaf role {
      type Yang2bag-string;
      description
        "The lsp role at the current node, whether it is
        headend, transit or tailend";
    }
  }

  grouping UNDERFLOW-STATE {
    description "UNDERFLOW STATE";
    leaf enabled {
      type boolean;
      description
        "enables bandwidth underflow adjustment on the
        lsp";
    }
    leaf underflow-threshold {
      type uint8;
      units "percentage";
      description
        "bandwidth percentage change to trigger and
        underflow event";
    }
    leaf trigger-event-count {
      type uint16;
      description
        "number of consecutive underflow sample events
        needed to trigger an underflow adjustment";
    }
  }

  grouping UNDERFLOW {
    description "UNDERFLOW";

    container state {
      description
        "State information for MPLS underflow bandwidth
        adjustment";
      uses UNDERFLOW-STATE;
    }
  }

  grouping OVERFLOW-STATE {
    description "OVERFLOW STATE";
    leaf enabled {
      type boolean;
      description
        "enables mpls lsp bandwidth overflow adjustment
        on the lsp";
    }
    leaf overflow-threshold {
      type uint8;
      units "percentage";
      description
        "bandwidth percentage change to trigger an
        overflow event";
    }
    leaf trigger-event-count {
      type uint16;
      description
        "number of consecutive overflow sample events
        needed to trigger an overflow adjustment";
    }
  }

  grouping OVERFLOW {
    description "OVERFLOW";

    container state {
      description
        "Config information for MPLS overflow bandwidth
        adjustment";
      uses OVERFLOW-STATE;
    }
  }

  grouping AUTO-BANDWIDTH-STATE {
    description "AUTO BANDWIDTH STATE";
    leaf enabled {
      type boolean;
      description "enables mpls auto-bandwidth on the lsp";
    }
    leaf min-bw {
      type uint64;
      units "kbit/s";
      description
        "set the minimum bandwidth in Kbps for an
        auto-bandwidth LSP";
    }
    leaf max-bw {
      type uint64;
      units "kbit/s";
      description
        "set the maximum bandwidth in Kbps for an
        auto-bandwidth LSP";
    }
    leaf adjust-interval {
      type uint32;
      units "second";
      description
        "time in seconds between adjustments to LSP
        bandwidth";
    }
    leaf adjust-threshold {
      type uint8;
      units "percentage";
      description
        "percentage difference between the LSP's
        specified bandwidth and its current bandwidth
        allocation -- if the difference is greater than
        the specified percentage, auto-bandwidth
        adjustment is triggered";
    }
  }

  grouping AUTO-BANDWIDTH {
    description "AUTO BANDWIDTH";

    container state {
      description
        "State parameters relating to MPLS auto-bandwidth
        on the tunnel";
      uses AUTO-BANDWIDTH-STATE;
    }

    container overflow {
      description
        "configuration of MPLS overflow bandwidth
        adjustement for the LSP";
      uses OVERFLOW;
    }

    container underflow {
      description
        "configuration of MPLS underflow bandwidth
        adjustement for the LSP";
      uses UNDERFLOW;
    }
  }

  grouping BANDWIDTH-STATE {
    description "BANDWIDTH STATE";
    leaf specification-type {
      type Openconfig-mpls-te-te-bandwidth-type-enum;
      description
        "The method used for settign the bandwidth,
        either explicitly specified or configured";
    }
    leaf set-bandwidth {
      type uint64;
      description "set bandwidth explicitly, e";
    }
    leaf signaled-bandwidth {
      type uint64;
      description "The currently signaled bandwidth of the LSP";
    }
  }

  grouping OVERLAY-OCNI-MPLS-TE-BANDWIDTH {
    description "Bandwidth configuration for TE LSPs";

    container state {
      description
        "State parameters related to bandwidth
        configuration of TE tunnels";
      uses BANDWIDTH-STATE;
    }

    container auto-bandwidth {
      description "Parameters related to auto-bandwidth";
      uses AUTO-BANDWIDTH;
    }
  }

  grouping OVERLAY-OCNI-MPLS-TE-NAMED-EXPLICIT-PATH-STATE {
    description
      "Operational state parameters relating to the
      named explicit paths";
    leaf name {
      type Yang2bag-string;
      description
        "A string name that uniquely identifies an
        explicit path";
    }
  }

  grouping EXPLICIT-ROUTE-OBJECT-STATE {
    description "EXPLICIT ROUTE OBJECT STATE";
    leaf address {
      type Yang2bag-string;
      description "router hop for the LSP path";
    }
    leaf hop-type {
      type Openconfig-mpls-te-mpls-hop-type-enum;
      description "strict or loose hop";
    }
    leaf index {
      type uint8;
      description
        "Index of this explicit route object to express
        the order of hops in the path";
    }
  }

  grouping OVERLAY-OCNI-MPLS-TE-EXPLICIT-ROUTE-OBJECT {
    description "List of explicit route objects";

    container state {
      description "State parameters relating to an explicit route";
      uses EXPLICIT-ROUTE-OBJECT-STATE;
    }
  }

  grouping STATE {
    description "STATE";
    leaf null-label {
      type Yang2bag-string;
      description "The null-label type used, implicit or explicit";
    }
  }

  grouping OVERLAY-OCNI-MPLS-TE-GLOBAL {
    description
      "general mpls configuration applicable to any type
      of LSP and signaling protocol - label ranges,
      entropy label supportmay be added here";

    container state {
      description "Top level global MPLS state";
      uses STATE;
    }
  }
}
