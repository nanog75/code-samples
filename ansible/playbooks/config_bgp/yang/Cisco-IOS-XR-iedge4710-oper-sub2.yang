submodule Cisco-IOS-XR-iedge4710-oper-sub2 {

  belongs-to Cisco-IOS-XR-iedge4710-oper {
    prefix Cisco-IOS-XR-iedge4710-oper;
  }

  /*** LINKAGE (IMPORTS / INCLUDES) ***/

  import ietf-inet-types { prefix "inet"; }

  import ietf-yang-types { prefix "yang"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR iedge4710 package operational data.

     Copyright (c) 2013-2018 by Cisco Systems, Inc.
     All rights reserved.";

  revision "2018-09-20" {
    description
      "Fixed yang gaps.";
  }

  revision "2015-11-09" {
    description
      "IOS XR 6.0 revision.";
  }

  typedef Iedge-oper-service-status {
    type enumeration {
      enum unknown {
        description "Unknown";
      }
      enum error {
        description "Error";
      }
      enum new {
        description "New";
      }
      enum loading {
        description "Loading";
      }
      enum req-association {
        description "Request Association";
      }
      enum associated {
        description "Associated";
      }
      enum req-pd-association {
        description "Request PD Association";
      }
      enum applied {
        description "Applied";
      }
      enum req-unassociation {
        description "Request Unassociation";
      }
      enum req-pd-unassociation {
        description "Request PD Unassociation";
      }
      enum unapplied {
        description "Unapplied";
      }
      enum max {
        description "Max";
      }
    }
    description "Subscriber service status";
  }
  typedef Iedge-oper-service {
    type enumeration {
      enum unknown {
        description "Unknown Service";
      }
      enum profile {
        description "Profile";
      }
      enum template {
        description "Template";
      }
      enum grp-template {
        description "GRP Template";
      }
      enum ppp-template {
        description "PPP Template";
      }
      enum eth-template {
        description "ETH Template";
      }
      enum ip-sub-template {
        description "IPSub Template";
      }
      enum multi-template {
        description "Multi Template";
      }
      enum max-templae {
        description "MAX Template";
      }
    }
    description "Service types";
  }
  typedef Iedge-oper-session-state {
    type enumeration {
      enum initialize {
        description "Initialize";
      }
      enum connecting {
        description "Connecting";
      }
      enum connected {
        description "Connected";
      }
      enum activated {
        description "Activated";
      }
      enum idle {
        description "Idle";
      }
      enum disconnecting {
        description "Disconnecting";
      }
      enum end {
        description "End";
      }
    }
    description "Subscriber session states";
  }
  typedef Mac-address {
    type yang:mac-address;
    description "MAC address type";
  }
  typedef Hex-binary {
    type yang:hex-string;
    description "Hex binary data";
  }
  typedef Ipv4-address {
    type inet:ipv4-address;
    description "IP address type";
  }
  typedef Iedge-ppp-sub {
    type enumeration {
      enum pta {
        description "PPP termination and aggregation";
      }
      enum lac {
        description "L2TP access controller";
      }
    }
    description "PPPoE sub types";
  }
  typedef Iedge-oper-session {
    type enumeration {
      enum unknown {
        description "Unknown";
      }
      enum pppoe {
        description "PPPoE/PPP client";
      }
      enum ppp {
        description "PPP serial client";
      }
      enum ip-packet-trigger {
        description "IP subscriber - packet trigger";
      }
      enum ip-packet-dhcp-trigger {
        description "IP subscriber - DHCP trigger";
      }
    }
    description "Subscriber session types";
  }

  grouping IEDGE-OPER-COA-DATA {
    description "IEDGE OPER COA DATA";
    leaf request-acked {
      type boolean;
      description "Coa Request Acked";
    }
    leaf request-time-epoch {
      type uint64;
      units "second";
      description "Request time in epoch seconds";
    }
    leaf reply-time-epoch {
      type uint64;
      units "second";
      description "Reply time in epoch seconds";
    }
  }

  grouping IEDGE-OPER-SERVICE-DATA {
    description "Subscriber service information";
    leaf service-name {
      type string;
      description "ServiceName";
    }
    leaf service-params {
      type string;
      description "ServiceParams";
    }
    leaf service-type {
      type Iedge-oper-service;
      description "ServiceType";
    }
    leaf service-status {
      type Iedge-oper-service-status;
      description "ServiceStatus";
    }
    leaf service-id {
      type uint32;
      description "ServiceIdentifier";
    }
    leaf service-prepaid {
      type boolean;
      description "ServicePrepaid";
    }
  }

  grouping IEDGE-POLICY-DATA {
    description "Subscriber policy information";
    leaf policy-epoch {
      type string;
      description "Matching event, condition and executed actions";
    }
  }

  grouping IEDGE-OPER-ACCOUNTING-DATA {
    description "Session/Service accounting information";
    leaf accounting-state-rc {
      type uint32;
      description
        "Accounting State Error Code for Accounting
        Session";
    }
    leaf accounting-stop-state {
      type uint32;
      description "Accounting Stop State";
    }
    leaf record-context-name {
      type string;
      description "Accounting record context name";
    }
    leaf method-list-name {
      type string;
      description "AAA method list name used to perform accounting";
    }
    leaf account-session-id {
      type string;
      description "Accounting session ID";
    }
    leaf accounting-start-time-epoch {
      type uint64;
      units "second";
      description "Accounting start time in epoch-seconds";
    }
    leaf is-interim-accounting-enabled {
      type boolean;
      description "True if interim accounting is enabled";
    }
    leaf interim-interval {
      type uint32;
      units "minute";
      description "Interim accounting interval (in minutes)";
    }
    leaf last-successful-interim-update-time-epoch {
      type uint64;
      units "second";
      description
        "Time of last successful interim update in
        epoch-seconds ";
    }
    leaf next-interim-update-attempt-time {
      type uint32;
      units "second";
      description
        "Time of next interim update attempt (in seconds)";
    }
    leaf last-interim-update-attempt-time-epoch {
      type uint64;
      units "second";
      description
        "Time of last interim update attempt in
        epoch-seconds";
    }
    leaf sent-interim-updates {
      type uint32;
      description "Number of interim updates sent";
    }
    leaf accepted-interim-updates {
      type uint32;
      description "Number of interim updates accepted";
    }
    leaf rejected-interim-updates {
      type uint32;
      description "Number of interim updates rejected";
    }
    leaf sent-interim-update-failures {
      type uint32;
      description "Number of interim update send failures";
    }
  }

  grouping IEDGE-ACCNT-DATA {
    description "Accounting information";

    list accounting-session {
      description "Accounting information";
      uses IEDGE-OPER-ACCOUNTING-DATA;
    }
  }

  grouping SUBSCRIBER-SESSION-DATA {
    description "Subscriber session information";

    container accounting {
      description "Accounting information";
      uses IEDGE-ACCNT-DATA;
    }
    leaf session-type {
      type Iedge-oper-session;
      description "Subscriber session type";
    }
    leaf pppoe-sub-type {
      type Iedge-ppp-sub;
      description "PPPoE sub type";
    }
    leaf interface-name {
      type xr:Interface-name;
      description "Interface name";
    }
    leaf vrf-name {
      type string;
      description "VRF name";
    }
    leaf circuit-id {
      type string;
      description "Circuit ID";
    }
    leaf remote-id {
      type string;
      description "Remote ID";
    }
    leaf lns-address {
      type Ipv4-address;
      description "PPPoE LNS address";
    }
    leaf lac-address {
      type Ipv4-address;
      description "PPPoE LAC address";
    }
    leaf tunnel-client-authentication-id {
      type string;
      description "PPPoE LAC tunnel client authentication ID";
    }
    leaf tunnel-server-authentication-id {
      type string;
      description "PPPoE LAC tunnel server authentication ID";
    }
    leaf session-ip-address {
      type Ipv4-address;
      description "Session ip address";
    }
    leaf session-ipv6-address {
      type string;
      description "Session IPv6 address";
    }
    leaf session-ipv6-prefix {
      type string;
      description "Session IPv6 prefix";
    }
    leaf delegated-ipv6-prefix {
      type string;
      description "Session delegated IPv6 prefix";
    }
    leaf ipv6-interface-id {
      type Hex-binary;
      description "IPv6 Interface ID";
    }
    leaf mac-address {
      type Mac-address;
      description "MAC address";
    }
    leaf account-session-id {
      type string;
      description "Accounting session ID";
    }
    leaf nas-port {
      type string;
      description "NAS port";
    }
    leaf username {
      type string;
      description "Username";
    }
    leaf clientname {
      type string;
      description "Client Username";
    }
    leaf formattedname {
      type string;
      description "Formatted Username";
    }
    leaf is-session-authentic {
      type boolean;
      description "If true, session is authentic";
    }
    leaf is-session-author {
      type boolean;
      description "If true, session is authorized";
    }
    leaf session-state {
      type Iedge-oper-session-state;
      description "Session state";
    }
    leaf session-creation-time-epoch {
      type uint64;
      units "second";
      description "Session creation time in epoch seconds";
    }
    leaf idle-state-change-time {
      type string;
      description
        "Time when idle state change occurred in DDD MMM
        DD HH:MM:SS YYYY format eg: Tue Apr 11 21:30:47
        2011";
    }
    leaf total-session-idle-time {
      type uint32;
      units "second";
      description "Total session idle time (in seconds)";
    }
    leaf access-interface-name {
      type xr:Interface-name;
      description
        "Access interface name associated with the
        session";
    }

    list sub-policy-data {
      description
        "Subscriber control policy applied to this
        session";
      uses IEDGE-POLICY-DATA;
    }

    list session-service-info {
      description
        "List of subscriber services associated to this
        session";
      uses IEDGE-OPER-SERVICE-DATA;
    }

    list session-change-of-authorization {
      description "Subscriber change of authorization information";
      uses IEDGE-OPER-COA-DATA;
    }
  }

  grouping SUBSCRIBER-SESSION-AF-COUNTS {
    description "Subscriber address family session counts";
    leaf in-progress-sessions {
      type uint32;
      description "Sessions with undecided address family";
    }
    leaf ipv4-only-sessions {
      type uint32;
      description "IPv4 only sessions ";
    }
    leaf ipv6-only-sessions {
      type uint32;
      description "IPv6 only sessions ";
    }
    leaf dual-part-up-sessions {
      type uint32;
      description "Dual stack partially up sessions";
    }
    leaf dual-up-sessions {
      type uint32;
      description "Dual stack up sessions";
    }
    leaf lac-sessions {
      type uint32;
      description "LAC sessions";
    }
  }

  grouping SUBSCRIBER-SESSION-AF-SUMMARY {
    description
      "Subscriber session address family summary
      information";

    container pppoe {
      description "PPPoE summary";
      uses SUBSCRIBER-SESSION-AF-COUNTS;
    }

    container ip-subscriber-dhcp {
      description "IP subscriber DHCP summary";
      uses SUBSCRIBER-SESSION-AF-COUNTS;
    }

    container ip-subscriber-packet {
      description "IP subscriber packet summary";
      uses SUBSCRIBER-SESSION-AF-COUNTS;
    }
  }

  grouping SUBSCRIBER-SESSION-STATE-COUNTS {
    description "Subscriber state session counts";
    leaf initialized-sessions {
      type uint32;
      description "Sessions in initialized state";
    }
    leaf connecting-sessions {
      type uint32;
      description "Sessions in connecting state";
    }
    leaf connected-sessions {
      type uint32;
      description "Sessions in connected state";
    }
    leaf activated-sessions {
      type uint32;
      description "Sessions in activated state";
    }
    leaf idle-sessions {
      type uint32;
      description "Sessions in idle state";
    }
    leaf disconnecting-sessions {
      type uint32;
      description "Sessions in disconnecting state";
    }
    leaf end-sessions {
      type uint32;
      description "Sessions in end state";
    }
  }

  grouping SUBSCRIBER-SESSION-STATE-SUMMARY {
    description "Subscriber session state summary information";

    container pppoe {
      description "PPPoE summary";
      uses SUBSCRIBER-SESSION-STATE-COUNTS;
    }

    container ip-subscriber-dhcp {
      description "IP subscriber DHCP summary";
      uses SUBSCRIBER-SESSION-STATE-COUNTS;
    }

    container ip-subscriber-packet {
      description "IP subscriber packet summary";
      uses SUBSCRIBER-SESSION-STATE-COUNTS;
    }
  }

  grouping SUBSCRIBER-SESSION-SUMMARY {
    description "Subscriber session summary information";

    container state-xr {
      description "State summary";
      uses SUBSCRIBER-SESSION-STATE-SUMMARY;
    }

    container address-family-xr {
      description "Address family summary";
      uses SUBSCRIBER-SESSION-AF-SUMMARY;
    }
  }
}
