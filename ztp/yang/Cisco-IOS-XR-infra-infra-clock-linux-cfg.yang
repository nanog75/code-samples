module Cisco-IOS-XR-infra-infra-clock-linux-cfg {

  /*** NAMESPACE / PREFIX DEFINITION ***/

  namespace "http://cisco.com/ns/yang"+
    "/Cisco-IOS-XR-infra-infra-clock-linux-cfg";


  prefix "infra-infra-clock-linux-cfg";

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR infra-infra-clock-linux package configuration.

     This module contains definitions
     for the following management objects:
       clock: Configure time-of-day clock

     Copyright (c) 2013-2018 by Cisco Systems, Inc.
     All rights reserved.";

  revision "2015-11-09" {
    description
      "IOS XR 6.0 revision.";
  }


  container clock {
    description "Configure time-of-day clock";

    container time-zone {
      presence "Indicates a time-zone node is configured.";
      description "Configure time zone";
      leaf time-zone-name {
        type string;
        mandatory true;
        description "Name of time zone";
      }
      leaf area-name {
        type string;
        mandatory true;
        description "Area File in zoneinfo package";
      }
    }
  }
}
