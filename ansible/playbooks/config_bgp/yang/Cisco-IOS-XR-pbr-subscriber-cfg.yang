module Cisco-IOS-XR-pbr-subscriber-cfg {

  /*** NAMESPACE / PREFIX DEFINITION ***/

  namespace "http://cisco.com/ns"+
    "/yang/Cisco-IOS-XR-pbr-subscriber-cfg";


  prefix "pbr-subscriber-cfg";

  /*** LINKAGE (IMPORTS / INCLUDES) ***/

  import Cisco-IOS-XR-subscriber-infra-tmplmgr-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR pbr-subscriber package configuration.

     This YANG module augments the
       Cisco-IOS-XR-subscriber-infra-tmplmgr-cfg
     module with configuration data.

     Copyright (c) 2013-2018 by Cisco Systems, Inc.
     All rights reserved.";

  revision "2015-11-09" {
    description
      "IOS XR 6.0 revision.";
  }


  grouping PBR {
    description
      "Common node of ip-subscriber, subscriber-service,
      ppp";

    container pbr {
      description "Dynamic Template PBR configuration";

      container service-policy {
        description "PBR service policy configuration";
        leaf input {
          type string;
          description "Ingress service policy";
        }
      }
      leaf service-policy-in {
        type string;
        description "Class for subscriber ingress policy";
      }
    }
  }

  augment "/a1:dynamic-template/a1:ppps/a1:ppp" {
    description
      "This augment extends the configuration data of
      'Cisco-IOS-XR-subscriber-infra-tmplmgr-cfg'";
    uses PBR;
  }

  augment "/a1:dynamic-template/a1:subscriber-services"+
    "/a1:subscriber-service" {
    description
      "This augment extends the configuration data of
      'Cisco-IOS-XR-subscriber-infra-tmplmgr-cfg'";
    uses PBR;
  }

  augment "/a1:dynamic-template/a1:ip-subscribers/a1:ip-subscriber" {
    description
      "This augment extends the configuration data of
      'Cisco-IOS-XR-subscriber-infra-tmplmgr-cfg'";
    uses PBR;
  }
}
