module Cisco-IOS-XR-controller-odu-datatypes {

  /*** NAMESPACE / PREFIX DEFINITION ***/

  namespace "http://cisco.com/ns/yang"+
    "/Cisco-IOS-XR-controller-odu-datatypes";


  prefix "controller-odu-datatypes";

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of generally useful
     derived YANG data types.

     Copyright (c) 2013-2018 by Cisco Systems, Inc.
     All rights reserved.";

  revision "2015-11-09" {
    description
      "IOS XR 6.0 revision.";
  }

  typedef Otn-child-controller-name {
    type enumeration {
      enum odu1 {
        value 1;
        description "Create lower order odu1 controller";
      }
      enum odu2 {
        value 2;
        description "Create lower order odu2 controller";
      }
      enum odu3 {
        value 3;
        description "Create lower order odu3 controller";
      }
      enum odu0 {
        value 10;
        description "Create lower order odu0 controller";
      }
      enum odu2e {
        value 11;
        description "Create lower order odu2e controller";
      }
      enum odu1e {
        value 23;
        description "Create lower order odu1e controller";
      }
      enum odu2f {
        value 25;
        description "Create lower order odu2f controller";
      }
      enum odu3e1 {
        value 26;
        description "Create lower order odu3e1 controller";
      }
      enum odu3e2 {
        value 27;
        description "Create lower order odu3e2 controller";
      }
    }
    description "Otn child controller name";
  }
  typedef Otn-child-flex-controller-name {
    type enumeration {
      enum odu-flex {
        value 22;
        description "Create lower order odu-flex controller";
      }
    }
    description "Otn child flex controller name";
  }
  typedef Otn-flex-mapping {
    type enumeration {
      enum gfp-f-fixed {
        value 1;
        description "GFP-FIX Mapping";
      }
      enum gfp-resizable {
        value 2;
        description "GFP-Resizable Mapping";
      }
      enum cbr {
        value 3;
        description "CBR Mapping";
      }
    }
    description "Otn flex mapping";
  }
  typedef Otntcm-mode {
    type enumeration {
      enum transparent {
        value 0;
        description "Set TCM Mode as transparent";
      }
      enum nim {
        value 1;
        description "Set TCM Mode as NIM";
      }
      enum operational {
        value 2;
        description "Set TCM Mode as operational";
      }
    }
    description "Otntcm mode";
  }
  typedef Otn-per-mon {
    type enumeration {
      enum disable {
        value 0;
        description "Performance Monitoring Disabled";
      }
      enum enable {
        value 1;
        description "Performance Monitoring Enabled";
      }
    }
    description "Otn per mon";
  }
  typedef Odu-time-slot-granularity {
    type enumeration {
      enum 1.25g {
        value 0;
        description "1.25G time slot granularity";
      }
      enum 2.5g {
        value 1;
        description "2.5G time slot granularity";
      }
    }
    description "Odu time slot granularity";
  }
  typedef Mode {
    type enumeration {
      enum mode-invalid {
        value 0;
        description "prbs Mode Invalid";
      }
      enum mode-source {
        value 1;
        description "Prbs Mode Source";
      }
      enum mode-sink {
        value 2;
        description "Prbs Mode Sink";
      }
      enum mode-source-sink {
        value 3;
        description "Prbs Mode Source_Sink";
      }
    }
    description "Mode";
  }
  typedef Otn-send-tti-type-os {
    type enumeration {
      enum send-tti-os-ascii/os-ascii {
        value 10;
        description "Send TTI OS ASCII string";
      }
      enum send-tti-os-hex/os-hex {
        value 12;
        description "Send TTI OS HEX string";
      }
    }
    description "Otn send tti type os";
  }
  typedef Otn-exp-tti-type-sapi {
    type enumeration {
      enum exp-tti-sapi-ascii/sapi-ascii {
        value 15;
        description "Expected TTI SAPI ASCII string";
      }
    }
    description "Otn exp tti type sapi";
  }
  typedef Otn-termination {
    type enumeration {
      enum ether {
        value 1;
        description "Termination to ether";
      }
    }
    description "Otn termination";
  }
  typedef Otn-send-tti-type-sapi {
    type enumeration {
      enum send-tti-sapi-ascii/sapi-ascii {
        value 14;
        description "Send TTI SAPI ASCII string";
      }
    }
    description "Otn send tti type sapi";
  }
  typedef Otn-sec-admin-state {
    type enumeration {
      enum normal {
        value 0;
        description "In normal state";
      }
      enum maintenance {
        value 1;
        description "Under maintenance";
      }
    }
    description "Otn sec admin state";
  }
  typedef Otn-mapping {
    type enumeration {
      enum gfp-f {
        value 1;
        description "gfp_f for mapping";
      }
      enum bmp {
        value 3;
        description "bmp for mapping";
      }
      enum gmp {
        value 4;
        description "gmp for mapping";
      }
      enum gfp-f-ext {
        value 6;
        description "gfp_f_ext for mapping";
      }
    }
    description "Otn mapping";
  }
  typedef Otn-exp-tti-type-os {
    type enumeration {
      enum exp-tti-os-ascii/os-ascii {
        value 11;
        description "Expected TTI OS ASCII string";
      }
      enum exp-tti-os-hex/os-hex {
        value 13;
        description "Expected TTI OS HEX string";
      }
    }
    description "Otn exp tti type os";
  }
  typedef Odu-delay {
    type enumeration {
      enum disable {
        value 0;
        description "Delay Disable";
      }
      enum enable {
        value 1;
        description "Delay Enable";
      }
    }
    description "Odu delay";
  }
  typedef Otn-loopback {
    type enumeration {
      enum line {
        value 2;
        description "Line loopback";
      }
      enum internal {
        value 4;
        description "Internal loopback";
      }
    }
    description "Otn loopback";
  }
  typedef Otn-exp-tti-type-full {
    type enumeration {
      enum exp-tti-full-ascii/full-ascii {
        value 5;
        description "Expected TTI Full ASCII string";
      }
      enum exp-tti-hex/hex {
        value 7;
        description "Expected TTI hex string";
      }
    }
    description "Otn exp tti type full";
  }
  typedef Otn-send-tti-type-full {
    type enumeration {
      enum send-tti-full-ascii/full-ascii {
        value 4;
        description "Send TTI Full ASCII string";
      }
      enum send-tti-hex/hex {
        value 6;
        description "Send TTI hex string";
      }
    }
    description "Otn send tti type full";
  }
  typedef Otn-exp-tti-type-dapi {
    type enumeration {
      enum exp-tti-dapi-ascii/dapi-ascii {
        value 9;
        description "Expected TTI DAPI ASCII string";
      }
    }
    description "Otn exp tti type dapi";
  }
  typedef Otn-send-tti-type-dapi {
    type enumeration {
      enum send-tti-dapi-ascii/dapi-ascii {
        value 8;
        description "Send TTI DAPI ASCII string";
      }
    }
    description "Otn send tti type dapi";
  }
  typedef Otntcmca {
    type enumeration {
      enum disable {
        value 0;
        description "Consequent(ial) action for Disabled";
      }
      enum enable {
        value 1;
        description "consequent(ial) action for Enabled";
      }
    }
    description "Otntcmca";
  }
  typedef Pattern {
    type enumeration {
      enum pattern-none {
        value 0;
        description "prbs pattern None";
      }
      enum pattern-pn31 {
        value 1;
        description "Prbs pattern pn31";
      }
      enum pattern-pn23 {
        value 2;
        description "Prbs pattern pn23";
      }
      enum pattern-pn11 {
        value 4;
        description "Prbs pattern pn11";
      }
      enum pattern-inverted-pn31 {
        value 8;
        description "Prbs pattern inverted pn31";
      }
      enum pattern-inverted-pn11 {
        value 16;
        description "Prbs pattern inverted pn11";
      }
    }
    description "Pattern";
  }
  typedef Otnpmtimca {
    type enumeration {
      enum disable {
        value 0;
        description "Path layer PM TIM Consequent action Disabled";
      }
      enum enable {
        value 1;
        description "Path layer PM TIM Consequent action  Enabled";
      }
    }
    description "Otnpmtimca";
  }
}
