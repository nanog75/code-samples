module Cisco-IOS-XR-lib-keychain-masterkey-aes-cfg {

  /*** NAMESPACE / PREFIX DEFINITION ***/

  namespace "http://cisco.com/ns/yang"+
    "/Cisco-IOS-XR-lib-keychain-masterkey-aes-cfg";


  prefix "lib-keychain-masterkey-aes-cfg";

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR lib-keychain-masterkey-aes package configuration.

     This module contains definitions
     for the following management objects:
       password: Configure masterkey

     Copyright (c) 2013-2018 by Cisco Systems, Inc.
     All rights reserved.";

  revision "2017-09-07" {
    description
      "Fixed type translation error.";
  }

  revision "2015-11-09" {
    description
      "IOS XR 6.0 revision.";
  }

  typedef Key-encryption {
    type enumeration {
      enum type6 {
        value 2;
        description "Type6";
      }
    }
    description "Key encryption";
  }

  container password {
    description "Configure masterkey";

    container encryption {
      description "Enable password encryption";
      leaf aes {
        type Key-encryption;
        description "encryption type used to store key";
      }
    }
  }
}
