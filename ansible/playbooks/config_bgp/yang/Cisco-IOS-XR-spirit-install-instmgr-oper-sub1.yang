submodule Cisco-IOS-XR-spirit-install-instmgr-oper-sub1 {

  belongs-to Cisco-IOS-XR-spirit-install-instmgr-oper {
    prefix Cisco-IOS-XR-spirit-install-instmgr-oper;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR spirit-install-instmgr package operational data.

     Copyright (c) 2013-2018 by Cisco Systems, Inc.
     All rights reserved.";

  revision "2019-08-24" {
    description
      "Changed model structure for software version and deprecated img-info node.";
  }

  revision "2017-09-07" {
    description
      "Fixed type translation error.";
  }

  revision "2017-07-24" {
    description
      "Fixing backward compatibility error in module.";
  }

  revision "2015-11-09" {
    description
      "IOS XR 6.0 revision.";
  }

  typedef Node-role-et {
    type enumeration {
      enum node-unknown {
        description "Unknown";
      }
      enum node-active {
        description "Active";
      }
      enum node-standby {
        description "Standby";
      }
      enum node-unusable {
        description "Unusable";
      }
    }
    description "node role";
  }
  typedef Issudir-node-status-et {
    type enumeration {
      enum not-issu-ready {
        description "Not ISSU Ready";
      }
      enum issu-ready {
        description "ISSU Ready";
      }
      enum isus-go {
        description "ISSU Go";
      }
      enum node-fail {
        description "Node Fail";
      }
    }
    description "ISSU node status";
  }
  typedef Issu-node-role-et {
    type enumeration {
      enum unknown-role {
        description "Unknown";
      }
      enum primary-role {
        description "Primary";
      }
      enum secondary-role {
        description "Secondary";
      }
      enum tertiary-role {
        description "Tertiary";
      }
    }
    description "ISSU role";
  }
  typedef Card-type-et {
    type enumeration {
      enum card-rp {
        description "Card RP";
      }
      enum card-drp {
        description "Card DRP";
      }
      enum card-lc {
        description "Card LC";
      }
      enum card-sc {
        description "Card SC";
      }
      enum card-sp {
        description "Card SP";
      }
      enum card-other {
        description "Card Other";
      }
    }
    description "card type";
  }
  typedef Isd-error-et {
    type enumeration {
      enum none {
        description "ISD ERROR NONE";
      }
      enum not-compatible {
        description "ISD ERROR NOT COMPATIBLE";
      }
      enum not-enough-resource {
        description "ISD ERROR NOT ENOUGH RESOURCE";
      }
      enum not-nsr-ready {
        description "ISD ERROR NOT NSR READY";
      }
      enum not-conn-sdrsm {
        description "ISD ERROR NOT CONNECTED SDR SM";
      }
      enum cmd-invalid {
        description "ISD ERROR INST CMD INVALID";
      }
      enum load-prep-fail {
        description "ISD ERROR INST LOAD PREP FAILURE";
      }
      enum error-timeout {
        description "ISD ERROR TIMEOUT";
      }
      enum err-node-down {
        description "ISD ERROR NODE DOWN";
      }
      enum node-not-ready {
        description "ISD ERROR NODE NOT READY";
      }
      enum err-node-new {
        description "ISD ERROR NODE NEW";
      }
      enum err-card-oir {
        description "ISD ERROR CARD OIR";
      }
      enum invalid-evt {
        description "ISD ERROR INVALID EVT";
      }
      enum disconn-from-calv {
        description "ISD ERROR DISCONN FROM CALVADOS";
      }
      enum gsp-down {
        description "ISD ERROR GSP DOWN";
      }
      enum abort-by-ism {
        description "ISD ERROR ABORT BY ISM";
      }
      enum rpfo {
        description "ISD ERROR RPFO";
      }
      enum pkg-null {
        description "ISD ERROR PKG NULL";
      }
      enum error-general {
        description "ISD ERROR GENERAL";
      }
      enum fsa-error {
        description "ISD ERROR FSA ERROR";
      }
      enum err-post-issu {
        description "ISD ERROR POST ISSU";
      }
      enum err-issu-dir-restart {
        description "ISD ERROR ISSUDIR RESTART";
      }
    }
    description "isd error";
  }
  typedef Isd-issu-status-et {
    type enumeration {
      enum ok {
        description "ISSU STATUS OK";
      }
      enum prep-done {
        description "ISSU STATUS PREP DONE";
      }
      enum big-bang {
        description "ISSU STATUS BIG BANG";
      }
      enum done {
        description "ISSU STATUS DONE";
      }
      enum abort {
        description "ISSU STATUS ABORT";
      }
      enum cmd-reject {
        description "ISSU STATUS CMD REJECT";
      }
      enum unknown {
        description "ISSU STATUS UNKNOWN";
      }
      enum abort-cleanup {
        description "ISSU STATUS ABORT CLEANUP";
      }
      enum abort-cmd-reject {
        description "ISSU STATUS CMD ABORT REJECT";
      }
    }
    description "isd status";
  }
  typedef Isd-state-et {
    type enumeration {
      enum none {
        description "ISSU ST NONE";
      }
      enum idle {
        description "ISSU ST IDLE";
      }
      enum init {
        description "ISSU ST INIT";
      }
      enum init-done {
        description "ISSU ST INIT DONE";
      }
      enum load-prep {
        description "ISSU ST LOAD PREP";
      }
      enum load-exec {
        description "ISSU ST LOAD EXEC";
      }
      enum load-issu-go {
        description "ISSU ST LOAD ISSU GO";
      }
      enum load-done {
        description "ISSU ST LOAD DONE";
      }
      enum run-prep-isd {
        description "ISSU ST RUN PREP ISD";
      }
      enum run-prep-ism {
        description "ISSU ST RUN PREP ISM";
      }
      enum big-bang {
        description "ISSU ST RUN BIG BANG";
      }
      enum run-done {
        description "ISSU ST RUN DONE";
      }
      enum cleanup {
        description "ISSU ST CLEANUP";
      }
      enum cleanup-done {
        description "ISSU ST CLEANUP DONE";
      }
      enum abort {
        description "ISSU ST ABORT";
      }
      enum abort-done {
        description "ISSU ST ABORT DONE";
      }
      enum abort-cleanup {
        description "ISSU ST ABORT CLEANUP";
      }
      enum unknown-state {
        description "ISSU UNKNOWN STATE";
      }
    }
    description "isd state";
  }

  grouping ISD-INV-INFO {
    description "ISSU Inventory Information";
    leaf node-id {
      type int32;
      description "Node ID";
    }
    leaf node-type {
      type Card-type-et;
      description "Node Type";
    }
    leaf issu-node-role {
      type Issu-node-role-et;
      description "ISSU Node Role";
    }
    leaf node-state {
      type Issudir-node-status-et;
      description "Node State";
    }
    leaf node-role {
      type Node-role-et;
      description "Node role";
    }
  }

  grouping ISD-INV-INFO-CONTAINER {
    description "ISSU Inventory Information all nodes";

    list invinfo {
      description "invinfo";
      uses ISD-INV-INFO;
    }
  }

  grouping ISD-STAGE-INFO {
    description "ISSU Director stage Information";
    leaf state {
      type Isd-state-et;
      description "State";
    }
    leaf issu-node-cnt {
      type int32;
      description "ISSU Node Count";
    }
    leaf issu-ready-node-cnt {
      type int32;
      description "ISSU Ready Node Count";
    }
    leaf percentage {
      type int32;
      units "percentage";
      description "Percentage";
    }
    leaf issu-status {
      type Isd-issu-status-et;
      description "Abort Status";
    }
    leaf issu-error {
      type Isd-error-et;
      description "ISSU Error";
    }
  }
}
