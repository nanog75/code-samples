submodule Cisco-IOS-XR-PRIVATE-ocni-mpls-rsvp-oper-sub1 {

  belongs-to Cisco-IOS-XR-PRIVATE-ocni-mpls-rsvp-oper {
    prefix Cisco-IOS-XR-PRIVATE-ocni-mpls-rsvp-oper;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR PRIVATE-ocni-mpls-rsvp package operational data.

     Copyright (c) 2013-2018 by Cisco Systems, Inc.
     All rights reserved.";

  revision "2015-11-09" {
    description
      "IOS XR 6.0 revision.";
  }

  typedef Openconfig-mpls-rsvp-neighbor-status-enum {
    type enumeration {
      enum up {
        value 0;
        description
          "RSVP hello messages are detected from the
          neighbor";
      }
      enum down {
        value 1;
        description
          "RSVP neighbor not detected as up, due to a
          communication failure or IGP notification the
          neighbor is unavailable";
      }
    }
    description "Openconfig mpls rsvp neighbor status enum";
  }
  typedef Openconfig-mpls-rsvp-status-enum {
    type enumeration {
      enum up {
        value 0;
        description "RSVP session is up";
      }
      enum down {
        value 1;
        description "RSVP session is down";
      }
    }
    description "Openconfig mpls rsvp status enum";
  }
  typedef Yang2bag-string {
    type string;
    description "Yang2bag string";
  }

  grouping NEIGHBOR-STATE {
    description "NEIGHBOR STATE";
    leaf address {
      type Yang2bag-string;
      description "Address of RSVP neighbor";
    }
    leaf detected-interface {
      type Yang2bag-string;
      description "Interface where RSVP neighbor was detected";
    }
    leaf neighbor-status {
      type Openconfig-mpls-rsvp-neighbor-status-enum;
      description "Enumuration of possible RSVP neighbor states";
    }
    leaf refresh-reduction {
      type boolean;
      description "Suppport of neighbor for RSVP refresh reduction";
    }
  }

  grouping OVERLAY-OCNI-MPLS-RSVP-NEIGHBOR {
    description "List of RSVP neighbors of the local system";

    container state {
      description
        "Operational state parameters relating to the
        RSVP neighbor";
      uses NEIGHBOR-STATE;
    }
  }

  grouping SUBSCRIPTION-STATE {
    description "SUBSCRIPTION STATE";
    leaf subscription {
      type uint8;
      units "percentage";
      description
        "percentage of the interface bandwidth that RSVP
        can reserve";
    }
    leaf calculated-absolute-subscription-bw {
      type uint64;
      description
        "The calculated absolute value of the bandwidth
        which is reservable to RSVP-TE on the interface
        prior to any adjustments that may be made from
        external sources";
    }
  }

  grouping SUBSCRIPTION {
    description "SUBSCRIPTION";

    container state {
      description
        "State parameters relating to RSVP subscription
        options";
      uses SUBSCRIPTION-STATE;
    }
  }

  grouping AUTHENTICATION-STATE {
    description "AUTHENTICATION STATE";
    leaf enable {
      type boolean;
      description "Enables RSVP authentication on the node";
    }
    leaf authentication-key {
      type Yang2bag-string;
      description "authenticate RSVP signaling messages";
    }
  }

  grouping AUTHENTICATION {
    description "AUTHENTICATION";

    container state {
      description
        "State information associated with authentication";
      uses AUTHENTICATION-STATE;
    }
  }

  grouping INTERFACE-HELLOS-STATE {
    description "INTERFACE HELLOS STATE";
    leaf hello-interval {
      type uint16;
      description
        "set the interval in ms between RSVP hello
        messages";
    }
    leaf refresh-reduction {
      type boolean;
      description
        "enables all RSVP refresh reduction message
        bundling, RSVP message ID, reliable message
        delivery and summary refresh";
    }
  }

  grouping INTERFACE-HELLOS {
    description "INTERFACE HELLOS";

    container state {
      description "State information associated with RSVP hellos";
      uses INTERFACE-HELLOS-STATE;
    }
  }

  grouping INTERFACE-REF-STATE {
    description "INTERFACE REF STATE";
    leaf interface {
      type Yang2bag-string;
      description "Reference to a base interface";
    }
    leaf subinterface {
      type uint32;
      description
        "Reference to a subinterface -- this requires the
        base interface to be specified using the
        interface leaf in this container";
    }
  }

  grouping INTERFACE-REF {
    description "INTERFACE REF";

    container state {
      description "Operational state for interface-ref";
      uses INTERFACE-REF-STATE;
    }
  }

  grouping STATE-COUNTERS {
    description "STATE COUNTERS";
    leaf in-path-messages {
      type uint64;
      description "Number of received RSVP Path messages";
    }
    leaf in-path-error-messages {
      type uint64;
      description "Number of received RSVP Path Error messages";
    }
    leaf in-path-tear-messages {
      type uint64;
      description "Number of received RSVP Path Tear messages";
    }
    leaf in-reservation-messages {
      type uint64;
      description "Number of received RSVP Resv messages";
    }
    leaf in-reservation-error-messages {
      type uint64;
      description "Number of received RSVP Resv Error messages";
    }
    leaf in-reservation-tear-messages {
      type uint64;
      description "Number of received RSVP Resv Tear messages";
    }
    leaf in-hello-messages {
      type uint64;
      description "Number of received RSVP hello messages";
    }
    leaf in-srefresh-messages {
      type uint64;
      description
        "Number of received RSVP summary refresh messages";
    }
    leaf in-ack-messages {
      type uint64;
      description
        "Number of received RSVP refresh reduction ack
        messages";
    }
    leaf out-path-messages {
      type uint64;
      description "Number of sent RSVP PATH messages";
    }
    leaf out-path-error-messages {
      type uint64;
      description "Number of sent RSVP Path Error messages";
    }
    leaf out-path-tear-messages {
      type uint64;
      description "Number of sent RSVP Path Tear messages";
    }
    leaf out-reservation-messages {
      type uint64;
      description "Number of sent RSVP Resv messages";
    }
    leaf out-reservation-error-messages {
      type uint64;
      description "Number of sent RSVP Resv Error messages";
    }
    leaf out-reservation-tear-messages {
      type uint64;
      description "Number of sent RSVP Resv Tear messages";
    }
    leaf out-hello-messages {
      type uint64;
      description "Number of sent RSVP hello messages";
    }
    leaf out-srefresh-messages {
      type uint64;
      description "Number of sent RSVP summary refresh messages";
    }
    leaf out-ack-messages {
      type uint64;
      description
        "Number of sent RSVP refresh reduction ack
        messages";
    }
  }

  grouping INTERFACE-STATE {
    description "INTERFACE STATE";

    container counters {
      description "Interface specific RSVP statistics and counters";
      uses STATE-COUNTERS;
    }
    leaf interface-id {
      type Yang2bag-string;
      description "Identifier for the interface";
    }
  }

  grouping OVERLAY-OCNI-MPLS-RSVP-INTERFACE {
    description "list of per-interface RSVP configurations";

    container state {
      description
        "Per-interface RSVP protocol and state
        information";
      uses INTERFACE-STATE;
    }

    container interface-ref {
      description "Reference to an interface or subinterface";
      uses INTERFACE-REF;
    }

    container hellos {
      description "Top level container for RSVP hello parameters";
      uses INTERFACE-HELLOS;
    }

    container authentication {
      description
        "Configuration and state parameters relating to
        RSVP authentication as per RFC2747";
      uses AUTHENTICATION;
    }

    container subscription {
      description
        "Bandwidth percentage reservable by RSVP on an
        interface";
      uses SUBSCRIPTION;
    }
  }

  grouping STATE {
    description "STATE";
    leaf index {
      type uint8;
      description "Index of object in the list";
    }
    leaf address {
      type Yang2bag-string;
      description "IP router hop for RRO entry";
    }
    leaf reported-label {
      type Yang2bag-string;
      description "Label reported for RRO hop";
    }
    leaf reported-flags {
      type uint8;
      description "Subobject flags for MPLS label";
    }
  }

  grouping OVERLAY-OCNI-MPLS-RSVP-RECORD-ROUTE-OBJECT {
    description
      "Read-only list of record route objects associated
      with the traffic engineered tunnel";

    container state {
      description "Information related to RRO objects";
      uses STATE;
    }
  }

  grouping SENDER-TSPEC {
    description "SENDER TSPEC";
    leaf rate {
      type Yang2bag-string;
      units "byte/s";
      description
        "The rate at which the head-end device generates
        traffic, expressed in bytes per second";
    }
    leaf size {
      type Yang2bag-string;
      units "byte/s";
      description
        "The size of the token bucket that is used to
        determine the rate at which the head-end device
        generates traffic, expressed in bytes per second";
    }
    leaf peak-data-rate {
      type Yang2bag-string;
      description
        "The maximum traffic generation rate that the
        head-end device sends traffic at";
    }
  }

  grouping OVERLAY-OCNI-MPLS-RSVP-STATE {
    description
      "Operational state parameters relating to the RSVP
      session";

    container sender-tspec {
      description
        "Operational state statistics relating to the
        SENDER_TSPEC received for the RSVP session";
      uses SENDER-TSPEC;
    }
    leaf local-index {
      type uint64;
      description
        "The index used to identify the RSVP session on
        the local network element";
    }
    leaf source-address {
      type Yang2bag-string;
      description "Origin address of RSVP session";
    }
    leaf destination-address {
      type Yang2bag-string;
      description "Destination address of RSVP session";
    }
    leaf tunnel-id {
      type uint16;
      description
        "The tunnel ID is an identifier used in the RSVP
        session, which remains constant over the life of
        the tunnel";
    }
    leaf lsp-id {
      type uint16;
      description
        "The LSP ID distinguishes between two LSPs
        originated from the same headend, and is
        commonly used to distinguish RSVP sessions
        during make before break operations";
    }
    leaf session-name {
      type Yang2bag-string;
      description "The signaled name of this RSVP session";
    }
    leaf status {
      type Openconfig-mpls-rsvp-status-enum;
      description "Enumeration of RSVP session states";
    }
    leaf type {
      type Yang2bag-string;
      description
        "The type/role of the RSVP session, signifing the
        session's role on the current device, such as a
        transit session vs";
    }
    leaf protection-requested {
      type Yang2bag-string;
      description
        "The type of protection requested for the RSVP
        session";
    }
    leaf label-in {
      type Yang2bag-string;
      description
        "Incoming MPLS label associated with this RSVP
        session";
    }
    leaf label-out {
      type Yang2bag-string;
      description
        "Outgoing MPLS label associated with this RSVP
        session";
    }
  }

  grouping COUNTERS {
    description "COUNTERS";
    leaf path-timeouts {
      type uint64;
      description "TODO";
    }
    leaf reservation-timeouts {
      type uint64;
      description "TODO";
    }
    leaf rate-limited-messages {
      type uint64;
      description "RSVP messages dropped due to rate limiting";
    }
    leaf in-path-messages {
      type uint64;
      description "Number of received RSVP Path messages";
    }
    leaf in-path-error-messages {
      type uint64;
      description "Number of received RSVP Path Error messages";
    }
    leaf in-path-tear-messages {
      type uint64;
      description "Number of received RSVP Path Tear messages";
    }
    leaf in-reservation-messages {
      type uint64;
      description "Number of received RSVP Resv messages";
    }
    leaf in-reservation-error-messages {
      type uint64;
      description "Number of received RSVP Resv Error messages";
    }
    leaf in-reservation-tear-messages {
      type uint64;
      description "Number of received RSVP Resv Tear messages";
    }
    leaf in-hello-messages {
      type uint64;
      description "Number of received RSVP hello messages";
    }
    leaf in-srefresh-messages {
      type uint64;
      description
        "Number of received RSVP summary refresh messages";
    }
    leaf in-ack-messages {
      type uint64;
      description
        "Number of received RSVP refresh reduction ack
        messages";
    }
    leaf out-path-messages {
      type uint64;
      description "Number of sent RSVP PATH messages";
    }
    leaf out-path-error-messages {
      type uint64;
      description "Number of sent RSVP Path Error messages";
    }
    leaf out-path-tear-messages {
      type uint64;
      description "Number of sent RSVP Path Tear messages";
    }
    leaf out-reservation-messages {
      type uint64;
      description "Number of sent RSVP Resv messages";
    }
    leaf out-reservation-error-messages {
      type uint64;
      description "Number of sent RSVP Resv Error messages";
    }
    leaf out-reservation-tear-messages {
      type uint64;
      description "Number of sent RSVP Resv Tear messages";
    }
    leaf out-hello-messages {
      type uint64;
      description "Number of sent RSVP hello messages";
    }
    leaf out-srefresh-messages {
      type uint64;
      description "Number of sent RSVP summary refresh messages";
    }
    leaf out-ack-messages {
      type uint64;
      description
        "Number of sent RSVP refresh reduction ack
        messages";
    }
  }

  grouping GLOBAL-STATE {
    description "GLOBAL STATE";

    container counters {
      description "Platform wide RSVP statistics and counters";
      uses COUNTERS;
    }
  }

  grouping HELLOS-STATE {
    description "HELLOS STATE";
    leaf hello-interval {
      type uint16;
      description
        "set the interval in ms between RSVP hello
        messages";
    }
    leaf refresh-reduction {
      type boolean;
      description
        "enables all RSVP refresh reduction message
        bundling, RSVP message ID, reliable message
        delivery and summary refresh";
    }
  }

  grouping HELLOS {
    description "HELLOS";

    container state {
      description "State information associated with RSVP hellos";
      uses HELLOS-STATE;
    }
  }

  grouping GRACEFUL-RESTART-STATE {
    description "GRACEFUL RESTART STATE";
    leaf enable {
      type boolean;
      description "Enables graceful restart on the node";
    }
    leaf restart-time {
      type uint32;
      units "second";
      description "Graceful restart time (seconds)";
    }
    leaf recovery-time {
      type uint32;
      description "RSVP state recovery time";
    }
  }

  grouping GRACEFUL-RESTART {
    description "GRACEFUL RESTART";

    container state {
      description
        "State information associated with RSVP
        graceful-restart";
      uses GRACEFUL-RESTART-STATE;
    }
  }

  grouping OVERLAY-OCNI-MPLS-RSVP-GLOBAL {
    description "Platform wide RSVP configuration and state";

    container graceful-restart {
      description
        "Operational state and configuration parameters
        relating to graceful-restart for RSVP";
      uses GRACEFUL-RESTART;
    }

    container hellos {
      description "Top level container for RSVP hello parameters";
      uses HELLOS;
    }

    container state {
      description "Platform wide RSVP state, including counters";
      uses GLOBAL-STATE;
    }
  }
}
