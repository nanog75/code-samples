module Cisco-IOS-XR-iedge4710-cfg {

  /*** NAMESPACE / PREFIX DEFINITION ***/

  namespace "http://cisco.com/ns/yang/Cisco-IOS-XR-iedge4710-cfg";


  prefix "iedge4710-cfg";

  /*** LINKAGE (IMPORTS / INCLUDES) ***/

  import Cisco-IOS-XR-types { prefix "xr"; }

  import Cisco-IOS-XR-ifmgr-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR iedge4710 package configuration.

     This module contains definitions
     for the following management objects:
       subscriber-manager: iEdge subscriber manager configuration
       subscriber-featurette: subscriber featurette
       iedge-license-manager: iedge license manager
       sub-manager: sub manager

     This YANG module augments the
       Cisco-IOS-XR-ifmgr-cfg
     module with configuration data.

     Copyright (c) 2013-2018 by Cisco Systems, Inc.
     All rights reserved.";

  revision "2017-09-07" {
    description
      "Fixed type translation error.";
  }

  revision "2015-11-09" {
    description
      "IOS XR 6.0 revision.";
  }


  container subscriber-manager {
    description "iEdge subscriber manager configuration";

    container accounting {
      description "iEdge accounting feature";

      container send-stop {
        description "Accounting send stop feature";

        container setup-failure {
          description "Setup failure feature";
          leaf method-list-name {
            type string;
            description
              "AAA List name either default or preconfigured";
          }
        }
      }

      container interim {
        description "interim accounting related";

        container variation {
          description
            "variation of first session or service interim
            record from configured timeout";
          leaf maximum-percentage-variation {
            type uint32 {
              range "0..50";
            }
            units "percentage";
            description
              "maximum percentage variation (maximum
              absolute variation is 15 minutes)";
          }
        }
      }
    }

    container srg {
      description "SRG specific config";
      leaf sync-account-session-id {
        type empty;
        description "sync account session id from master to slave";
      }
    }
  }

  container subscriber-featurette {
    description "subscriber featurette";

    list featurette-name {
      key "featurette";
      description "enable featurette processing";
      leaf enable {
        type uint32;
        description "instance of featurette";
      }
      leaf featurette {
        type xr:Cisco-ios-xr-string;
        description "subscriber feature";
      }
    }
  }

  container iedge-license-manager {
    description "iedge license manager";
    leaf session-limit {
      type uint32 {
        range "1..200000";
      }
      description "Session limit configured on linecard";
    }
  }

  container sub-manager {
    description "sub manager";

    list location {
      key "location1";
      description "Select location";

      container trace {
        description "Subscriber manager trace";
        leaf trace-level {
          type uint32;
          description "Subscriber manager trace level";
        }
      }
      leaf history {
        type empty;
        description "Disable history for subscriber manager";
      }
      leaf location1 {
        type xr:Cisco-ios-xr-string;
        description "Specify location";
      }
    }
  }

  augment "/a1:interface-configurations/a1:interface-configuration" {

    container service-policies {
      description
        "Interface control subscriber policy
        configuration";

      list service-policy {
        key "service-policy-name";
        description
          "Service policy to be applied to access
          interface  for subscribers";
        leaf service-policy-name {
          type string {
            length "1..63";
          }
          description "Name of policy-map";
        }
      }
    }
    description
      "This augment extends the configuration data of
      'Cisco-IOS-XR-ifmgr-cfg'";
  }
}
