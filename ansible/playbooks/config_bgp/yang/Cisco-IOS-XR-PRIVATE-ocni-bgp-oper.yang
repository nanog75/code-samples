module Cisco-IOS-XR-PRIVATE-ocni-bgp-oper {

  /*** NAMESPACE / PREFIX DEFINITION ***/

  namespace "http://cisco.com/ns/yang"+
    "/Cisco-IOS-XR-PRIVATE-ocni-bgp-oper";


  prefix "private-ocni-bgp-oper";

  /*** LINKAGE (IMPORTS / INCLUDES) ***/

  include Cisco-IOS-XR-PRIVATE-ocni-bgp-oper-sub1 {
    revision-date 2017-09-21;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR PRIVATE-ocni-bgp package operational data.

     This module contains definitions
     for the following management objects:
       ocni-bgp: An OpenConfig description of a network-instance

     Copyright (c) 2013-2018 by Cisco Systems, Inc.
     All rights reserved.";

  revision "2017-09-21" {
    description
      "Add openconfig network instance model BGP telemetry EDM function support.";
  }

  revision "2015-11-09" {
    description
      "IOS XR 6.0 revision.";
  }


  container ocni-bgp {
    config false;
    description "An OpenConfig description of a network-instance";

    container network-instances {
      description
        "Network instances configured on the local system";

      list network-instance {
        key "name";
        description
          "Network instances configured on the local
          system";

        container state {
          description
            "Operational state parameters relating to a
            network instance";
          uses OVERLAY-OCNI-BGP-STATE;
        }

        container protocols {
          description "A process (instance) of a routing protocol";

          list protocol {
            key "identifier name";
            description
              "A process (instance) of a routing protocol";

            container protocols-state {
              description
                "State parameters relating to the routing
                protocol instance";
              uses OVERLAY-OCNI-BGP-PROTOCOL-STATE;
            }

            container bgp {
              description
                "Top-level configuration and state for the
                BGP router";

              container global {
                description
                  "Global configuration for the BGP router";

                container global-state {
                  description
                    "State information relating to the global
                    BGP router";
                  uses OVERLAY-OCNI-BGP-GLOBAL-STATE;
                }

                container graceful-restart {
                  description
                    "Parameters relating the graceful restart
                    mechanism for BGP";
                  uses OVERLAY-OCNI-BGP-GRACEFUL-RESTART;
                }

                container confederation {
                  description
                    "Parameters indicating whether the local
                    system acts as part of a BGP confederation";
                  uses OVERLAY-OCNI-BGP-CONFEDERATION;
                }

                container afi-safis {
                  description
                    "AFI,SAFI configuration available for the
                    neighbour or group";

                  list afi-safi {
                    key "afi-safi-name";
                    description
                      "AFI,SAFI configuration available for the
                      neighbour or group";
                    leaf afi-safi-name {
                      type string;
                      description
                        "Reference to the AFI-SAFI name used as a
                        key for the AFI-SAFI list";
                    }
                    uses OVERLAY-OCNI-BGP-AFI-SAFI;
                  }
                }

                container default-route-distance {
                  description
                    "Administrative distance (or preference)
                    assigned to routes received from different
                    sources (external, internal, and local)";
                  uses OVERLAY-OCNI-BGP-DEFAULT-ROUTE-DISTANCE;
                }

                container use-multiple-paths {
                  description
                    "Parameters related to the use of multiple
                    paths for the same NLRI";
                  uses OVERLAY-OCNI-BGP-USE-MULTIPLE-PATHS;
                }

                container dynamic-neighbor-prefixes {
                  description
                    "An individual prefix from which dynamic
                    neighbor connections are allowed";

                  list dynamic-neighbor-prefixe {
                    key "prefix";
                    description
                      "An individual prefix from which dynamic
                      neighbor connections are allowed";
                    leaf prefix {
                      type string;
                      description
                        "Reference to the IP prefix from which
                        source connections are allowed for the
                        dynamic neighbor group";
                    }
                    uses OVERLAY-OCNI-BGP-DYNAMIC-NEIGHBOR-PREFIX;
                  }
                }

                container route-selection-options {
                  description
                    "Parameters relating to options for route
                    selection";
                  uses OVERLAY-OCNI-BGP-ROUTE-SELECTION-OPTIONS;
                }
              }

              container neighbors {
                description
                  "List of BGP neighbors configured on the
                  local system, uniquely identified by peer
                  IPv[46] address";

                list neighbor {
                  key "neighbor-address";
                  description
                    "List of BGP neighbors configured on the
                    local system, uniquely identified by peer
                    IPv[46] address";

                  container neighbors-state {
                    description
                      "State information relating to the BGP
                      neighbor";
                    uses OVERLAY-OCNI-BGP-NEIGHBOR-STATE;
                  }

                  container neighbors-use-multiple-paths {
                    description
                      "Parameters related to the use of
                      multiple-paths for the same NLRI when
                      they are received only from this neighbor";
                    uses "OVERLAY-OCNI-BGP"+
                      "-NEIGHBOR-USE-MULTIPLE-PATHS";
                  }

                  container neighbors-afi-safis {
                    description
                      "AFI,SAFI configuration available for the
                      neighbour or group";

                    list neighbors-afi-safi {
                      key "afi-safi-name";
                      description
                        "AFI,SAFI configuration available for the
                        neighbour or group";
                      leaf afi-safi-name {
                        type string;
                        description
                          "Reference to the AFI-SAFI name used as
                          a key for the AFI-SAFI list";
                      }
                      uses OVERLAY-OCNI-BGP-AFI-SAFIS-AFI-SAFI;
                    }
                  }

                  container neighbors-graceful-restart {
                    description
                      "Parameters relating the graceful restart
                      mechanism for BGP";
                    uses OVERLAY-OCNI-BGP-NEIGHBOR-GRACEFUL-RESTART;
                  }

                  container route-reflector {
                    description
                      "Route reflector parameters for the
                      BGPgroup";
                    uses OVERLAY-OCNI-BGP-ROUTE-REFLECTOR;
                  }

                  container apply-policy {
                    description
                      "Anchor point for routing policies in the
                      model";
                    uses OVERLAY-OCNI-BGP-APPLY-POLICY;
                  }

                  container add-paths {
                    description
                      "Parameters relating to the advertisement
                      and receipt of multiple paths for a
                      single NLRI (add-paths)";
                    uses OVERLAY-OCNI-BGP-ADD-PATHS;
                  }

                  container transport {
                    description
                      "Transport session parameters for the BGP
                      neighbor";
                    uses OVERLAY-OCNI-BGP-TRANSPORT;
                  }

                  container logging-options {
                    description
                      "Logging options for events related to the
                      BGP neighbor or group";
                    uses OVERLAY-OCNI-BGP-LOGGING-OPTIONS;
                  }

                  container as-path-options {
                    description
                      "AS_PATH manipulation parameters for the
                      BGP neighbor or group";
                    uses OVERLAY-OCNI-BGP-AS-PATH-OPTIONS;
                  }

                  container timers {
                    description "Timers related to a BGP neighbor";
                    uses OVERLAY-OCNI-BGP-TIMERS;
                  }

                  container error-handling {
                    description
                      "Error handling parameters used for the
                      BGP neighbor or group";
                    uses OVERLAY-OCNI-BGP-ERROR-HANDLING;
                  }

                  container ebgp-multihop {
                    description
                      "eBGP multi-hop parameters for the
                      BGPgroup";
                    uses OVERLAY-OCNI-BGP-EBGP-MULTIHOP;
                  }
                  leaf neighbor-address {
                    type string;
                    description
                      "Reference to the address of the BGP
                      neighbor used as a key in the neighbor
                      list";
                  }
                }
              }

              container peer-groups {
                description
                  "List of BGP peer-groups configured on the
                  local system - uniquely identified by
                  peer-group name";

                list peer-group {
                  key "peer-group-name";
                  description
                    "List of BGP peer-groups configured on the
                    local system - uniquely identified by
                    peer-group name";

                  container peer-groups-transport {
                    description
                      "Transport session parameters for the BGP
                      peer-group";
                    uses OVERLAY-OCNI-BGP-PEER-GROUP-TRANSPORT;
                  }

                  container peer-groups-timers {
                    description
                      "Timers related to a BGP peer-group";
                    uses OVERLAY-OCNI-BGP-PEER-GROUP-TIMERS;
                  }

                  container peer-groups-route-reflector {
                    description
                      "Route reflector parameters for the
                      BGPgroup";
                    uses OVERLAY-OCNI-BGP-PEER-GROUP-ROUTE-REFLECTOR;
                  }

                  container peer-groups-use-multiple-paths {
                    description
                      "Parameters related to the use of multiple
                      paths for the same NLRI";
                    uses "OVERLAY-OCNI-BGP-PEER"+
                      "-GROUP-USE-MULTIPLE-PATHS";
                  }

                  container peer-groups-logging-options {
                    description
                      "Logging options for events related to the
                      BGP neighbor or group";
                    uses OVERLAY-OCNI-BGP-PEER-GROUP-LOGGING-OPTIONS;
                  }

                  container peer-groups-add-paths {
                    description
                      "Parameters relating to the advertisement
                      and receipt of multiple paths for a
                      single NLRI (add-paths)";
                    uses OVERLAY-OCNI-BGP-PEER-GROUP-ADD-PATHS;
                  }

                  container peer-groups-as-path-options {
                    description
                      "AS_PATH manipulation parameters for the
                      BGP neighbor or group";
                    uses OVERLAY-OCNI-BGP-PEER-GROUP-AS-PATH-OPTIONS;
                  }

                  container peer-groups-afi-safis {
                    description
                      "AFI,SAFI configuration available for the
                      neighbour or group";

                    list peer-groups-afi-safi {
                      key "afi-safi-name";
                      description
                        "AFI,SAFI configuration available for the
                        neighbour or group";
                      leaf afi-safi-name {
                        type string;
                        description
                          "Reference to the AFI-SAFI name used as
                          a key for the AFI-SAFI list";
                      }
                      uses "OVERLAY-OCNI-BGP-PEER"+
                        "-GROUP-AFI-SAFIS-AFI-SAFI";
                    }
                  }

                  container peer-groups-state {
                    description
                      "State information relating to the BGP
                      peer-group";
                    uses OVERLAY-OCNI-BGP-PEER-GROUP-STATE;
                  }

                  container peer-groups-graceful-restart {
                    description
                      "Parameters relating the graceful restart
                      mechanism for BGP";
                    uses "OVERLAY-OCNI-BGP-PEER"+
                      "-GROUP-GRACEFUL-RESTART";
                  }

                  container peer-groups-error-handling {
                    description
                      "Error handling parameters used for the
                      BGP peer-group";
                    uses OVERLAY-OCNI-BGP-PEER-GROUP-ERROR-HANDLING;
                  }

                  container peer-groups-apply-policy {
                    description
                      "Anchor point for routing policies in the
                      model";
                    uses OVERLAY-OCNI-BGP-PEER-GROUP-APPLY-POLICY;
                  }

                  container peer-groups-ebgp-multihop {
                    description
                      "eBGP multi-hop parameters for the
                      BGPgroup";
                    uses OVERLAY-OCNI-BGP-PEER-GROUP-EBGP-MULTIHOP;
                  }
                  leaf peer-group-name {
                    type string;
                    description
                      "Reference to the name of the BGP
                      peer-group used as a key in the
                      peer-group list";
                  }
                }
              }
            }
            leaf identifier {
              type string;
              description
                "The protocol name for the routing or
                forwarding protocol to be instantiated";
            }
            leaf name {
              type string;
              description
                "An operator-assigned identifier for the
                routing or forwarding protocol";
            }
          }
        }
        leaf name {
          type string;
          description
            "A unique name identifying the network instance";
        }
      }
    }
  }
}
