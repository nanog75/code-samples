submodule Cisco-IOS-XR-fib-common-oper-sub4 {

  belongs-to Cisco-IOS-XR-fib-common-oper {
    prefix Cisco-IOS-XR-fib-common-oper;
  }

  /*** LINKAGE (IMPORTS / INCLUDES) ***/

  import ietf-inet-types { prefix "inet"; }

  import ietf-yang-types { prefix "yang"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR fib-common package operational data.

     Copyright (c) 2013-2018 by Cisco Systems, Inc.
     All rights reserved.";

  revision "2017-09-07" {
    description
      "Fixed type translation error.";
  }

  revision "2017-05-01" {
    description
      "Fixing backward compatibility error in module.";
  }

  revision "2017-01-20" {
    description
      "IOS XR 6.2.1 revision";
  }

  revision "2015-11-09" {
    description
      "IOS XR 6.0 revision.";
  }

  typedef Fib-mpls-llc-entry-bag {
    type enumeration {
      enum fib-mpls-llc-bag-type-xc {
        value 1;
        description "fib mpls llc bag type xc";
      }
      enum fib-mpls-llc-bag-type-pfx {
        value 2;
        description "fib mpls llc bag type pfx";
      }
      enum fib-mpls-llc-bag-type-lsm {
        value 3;
        description "fib mpls llc bag type lsm";
      }
      enum fib-mpls-llc-bag-type-max {
        value 4;
        description "fib mpls llc bag type max";
      }
    }
    description "Fib mpls llc entry bag";
  }
  typedef Fib-rpf-mode {
    type enumeration {
      enum fib-rpf-mode-strict {
        description "RPF mode strict";
      }
      enum fib-rpf-mode-loose {
        description "RPF mode loose";
      }
      enum fib-rpf-mode-unknown {
        description "RPF mode unknown";
      }
    }
    description "RPF mode types";
  }
  typedef Fibidb-oper {
    type enumeration {
      enum fibidb-none {
        value 0;
        description "fibidb none";
      }
      enum fibidb-create {
        value 1;
        description "fibidb create";
      }
      enum fibidb-delete {
        value 2;
        description "fibidb delete";
      }
      enum fibidb-modify {
        value 3;
        description "fibidb modify";
      }
      enum fibidb-max {
        value 4;
        description "fibidb max";
      }
    }
    description "Fibidb oper";
  }
  typedef Fib-sh-tbl-fib-ext-bag {
    type enumeration {
      enum leaf-extension {
        value 1;
        description "Leaf Extension";
      }
    }
    description "Fib sh tbl fib ext bag";
  }
  typedef Fib-update-path-lfa-protection {
    type enumeration {
      enum not-lfa-protected {
        description "Not LFA-protected";
      }
      enum local-lfa-protected {
        description "Local-LFA protected";
      }
      enum remote-lfa-protected {
        description "Remote-LFA protected";
      }
      enum ti-lfa-protected {
        description "TI-LFA protected";
      }
    }
    description "LFA protection type";
  }
  typedef Fib-sh-ipencap-hdr {
    type enumeration {
      enum fib-sh-ip-encap-none {
        description "No Header";
      }
      enum fib-sh-ip-encap-ip4 {
        description "IPv4 Header";
      }
      enum fib-sh-ip-encap-ip6 {
        description "IPv6 Header";
      }
      enum fib-sh-ip-encap-udp {
        description "UDP Header";
      }
      enum fib-sh-ip-encap-lisp {
        description "Lisp Header";
      }
    }
    description "IP Encap Header Type";
  }
  typedef Fib-neh-special {
    type enumeration {
      enum nh-not-found {
        description "nh not found";
      }
      enum nh-null0 {
        description "nh null0";
      }
      enum nh-punt {
        description "nh punt";
      }
      enum nh-drop {
        description "nh drop";
      }
      enum nh-glean {
        description "nh glean";
      }
      enum nh-receive {
        description "nh receive";
      }
      enum nh-broadcast {
        description "nh broadcast";
      }
      enum nh-external {
        description "nh external";
      }
      enum nh-lisp {
        description "nh lisp";
      }
      enum nh-lookup {
        description "nh lookup";
      }
      enum nh-max-type {
        description "nh max type";
      }
    }
    description "Fib neh special";
  }
  typedef Fib-neh {
    type enumeration {
      enum nh-local {
        description "nh local";
      }
      enum nh-remote {
        description "nh remote";
      }
      enum nh-special {
        description "nh special";
      }
    }
    description "Fib neh";
  }
  typedef Fib-adjacency-show {
    type enumeration {
      enum fib-adjacency-normal {
        description "Normal adjacency";
      }
      enum fib-adjacency-null {
        description "Null adjacency";
      }
      enum fib-adjacency-punt {
        description "Punt adjacency";
      }
      enum fib-adjacency-drop {
        description "Drop adjacency";
      }
      enum fib-adjacency-glean {
        description "Glean adjacency";
      }
      enum fib-adjacency-discard {
        description "Discard adjacency";
      }
      enum fib-adjacency-broadcast {
        description "Broadcast adjacency";
      }
      enum fib-adjacency-external {
        description "external adjacency";
      }
      enum fib-adjacency-lisp {
        description "LISP adjacency";
      }
      enum fib-adjacency-unknown {
        description "Unknown adjacency";
      }
    }
    description "Adjacency types";
  }
  typedef Fib-loadshare-show {
    type enumeration {
      enum fib-load-share-none {
        description "No loadsharing";
      }
      enum fib-load-share-per-packet {
        description "Per packet loadsharing";
      }
      enum fib-load-share-dest-sharing {
        description "Destination loadsharing";
      }
    }
    description "Loadsharing type";
  }
  typedef Fib-nhinfo-ext-bag {
    type enumeration {
      enum replicated-nh-info {
        description "Replicated NHINFO";
      }
      enum shared-nh-info {
        description "Shared NHINFO";
      }
    }
    description "FIB NHINFO extension type";
  }
  typedef Fib-frr-protocol-show {
    type enumeration {
      enum frr-protocol-ipv4 {
        description "frr protocol ipv4";
      }
      enum frr-protocol-ipv6 {
        description "frr protocol ipv6";
      }
      enum frr-protocol-mpls {
        description "frr protocol mpls";
      }
    }
    description "Fib frr protocol show";
  }
  typedef Ss-lba-state {
    type enumeration {
      enum l3 {
        description "L3 Load Balance config";
      }
      enum l4 {
        description "L4 Load Balance config";
      }
    }
    description "Load Balance config";
  }

  grouping FIB-MPLS-LLC-LSM {
    description "FIB MPLS LLC LSM";
    leaf nh {
      type string {
        length "0..52";
      }
      description "nh";
    }
    leaf mcast-id {
      type uint32;
      description "mcast id";
    }
  }

  grouping FIB-MPLS-LLC-PFX {
    description "FIB MPLS LLC PFX";
    leaf pfx {
      type string {
        length "0..52";
      }
      description "pfx";
    }
    leaf tbl-id {
      type uint32;
      description "tbl id";
    }
  }

  grouping FIB-MPLS-LLC-TYPE-EXT {
    description "FIB MPLS LLC TYPE EXT";

    container pfx {
      when "../type = 'fib-mpls-llc-bag-type-pfx'" {
        description "../type = 'FIB_MPLS_LLC_BAG_TYPE_PFX'";
      }
      description "pfx";
      uses FIB-MPLS-LLC-PFX;
    }

    container lsm {
      when "../type = 'fib-mpls-llc-bag-type-lsm'" {
        description "../type = 'FIB_MPLS_LLC_BAG_TYPE_LSM'";
      }
      description "lsm";
      uses FIB-MPLS-LLC-LSM;
    }
    leaf type {
      type Fib-mpls-llc-entry-bag;
      description "type";
    }
  }

  grouping FIB-MPLS-LLC {
    description "FIB MPLS LLC";

    container ext {
      description "ext";
      uses FIB-MPLS-LLC-TYPE-EXT;
    }
    leaf local-label {
      type uint32;
      description "local label";
    }
    leaf source-xr {
      type uint32;
      description "source xr";
    }
    leaf update-ts {
      type uint64;
      description "update ts";
    }
    leaf retry-ts {
      type uint64;
      description "retry ts";
    }
    leaf num-retries {
      type uint32;
      description "num retries";
    }
  }

  grouping FIB-SH-PLAT-CAPABILITIES {
    description "FIB platform capabilities";
    leaf fpc-num-l3-lbl-levels {
      type uint8;
      description "L3 LBL levels";
    }
    leaf fpc-num-l3-lbl-paths {
      type uint8;
      description "L3 Hash buckets";
    }
    leaf fpc-num-l3-lbl-rec-paths {
      type uint8;
      description "L3 Recursive Hash buckets";
    }
    leaf fpc-num-l3-ucmp-paths {
      type uint8;
      description "L3 Unequal cost hash buckets";
    }
    leaf fpc-num-fwding-stages {
      type uint8;
      description "Forwarding stages";
    }
    leaf fpc-local-label-split {
      type uint32;
      description "Label split";
    }
    leaf fpc-stats-support {
      type boolean;
      description "Statistics support";
    }
    leaf fpc-platf-ready-cb-wait {
      type boolean;
      description "Plat ready cb register";
    }
    leaf fpc-num-paths-per-pbts-class {
      type uint8;
      description "Path per tunnel class";
    }
    leaf fpc-platf-v4-upd-disable {
      type boolean;
      description "V4 update disable";
    }
    leaf fpc-platf-v6-upd-disable {
      type boolean;
      description "V6 update disable";
    }
    leaf fpc-lba-tuples-default {
      type uint32;
      description "LBA tuples";
    }
    leaf fpc-mraps-support {
      type boolean;
      description "MRAPS support";
    }
    leaf fpc-pbts-defclass-support {
      type boolean;
      description "PBTS default class support";
    }
    leaf fpc-loadinfo-filter-support {
      type boolean;
      description "loadinfo filter support";
    }
    leaf fpc-nhid {
      type boolean;
      description "NHID support";
    }
    leaf fpc-platf-temp-back-walk-reqd {
      type boolean;
      description "Backwalk dependents is required";
    }
    leaf fpc-link-mpls-nhinfo-in-ipv6-thread-support {
      type boolean;
      description "Link MPLS IPv6 NH support";
    }
    leaf fpc-exclude-deag-bkup {
      type boolean;
      description "Exclude Deag backup Paths";
    }
    leaf fpc-dlb-support {
      type boolean;
      description "Per-destination load-balancing support";
    }
    leaf fpc-prefix-filter-support {
      type uint8;
      description "Prefix filter level of support";
    }
    leaf fpc-slowpath-ingress-inject-reqd {
      type boolean;
      description "Slowpath ingress inject required";
    }
    leaf fpc-cofo-support {
      type boolean;
      description "COFO supported";
    }
    leaf fpc-srv6-support {
      type boolean;
      description "SRv6 supported";
    }
    leaf fpc-v4v6-ldi-collapse-support {
      type boolean;
      description "IPv4 over IPV6 Collapse LDI support";
    }

    list fpc-lisp-decap-over-v4 {
      min-elements "3";
      max-elements "3";
      description "LISP Decap over 4";
      leaf entry {
        type boolean;
        description "Array entry.";
      }
    }

    list fpc-lisp-decap-over-v6 {
      min-elements "3";
      max-elements "3";
      description "LISP Decap over 6";
      leaf entry {
        type boolean;
        description "Array entry.";
      }
    }

    list fpc-lisp-ucmp {
      min-elements "3";
      max-elements "3";
      description "LISP UCMP support";
      leaf entry {
        type boolean;
        description "Array entry.";
      }
    }

    list fpc-resolve-via-table {
      min-elements "3";
      max-elements "3";
      description "Fallback VRF support";
      leaf entry {
        type boolean;
        description "Array entry.";
      }
    }
  }

  grouping FIB-SH-PROTO-FRR-STATS {
    description "FIB per protocol frr counters";
    leaf mi-num-intf-frr {
      type uint32;
      description "number of FRR events sent on nh interface down";
    }
    leaf mi-num-parent-intf-frr {
      type uint32;
      description
        "number of FRR events sent on nh parent interface
        down";
    }
    leaf mi-num-pfi-intf-down {
      type uint32;
      description "number of interface down FRR events from PFI";
    }
    leaf mi-num-bfd-down {
      type uint32;
      description "number of NH down FRR events frm BFD";
    }
    leaf mi-num-prot-frr-objects {
      type uint32;
      description "total number of prot FRR objects";
    }
    leaf mi-num-bkup-frr-objects {
      type uint32;
      description "total number of backup FRR objects";
    }
    leaf mi-num-tunid-allocs {
      type uint32;
      description
        "total number of successful FRR tunnel ID
        allocations";
    }
    leaf mi-num-tunid-alloc-failures {
      type uint32;
      description
        "total number of FRR tunnel ID allocation
        failures";
    }
    leaf mi-num-tunid-frees {
      type uint32;
      description "total number of successful FRR tunnel ID frees";
    }
    leaf mi-num-tunid-free-failures {
      type uint32;
      description "total number of FRR tunnel ID free failures";
    }
    leaf mi-num-frr-reset-queue-adds {
      type uint32;
      description "number of frr reset queue adds";
    }
    leaf mi-num-frr-reset-queue-remove {
      type uint32;
      description "number of frr reset queue deletes";
    }
    leaf mi-num-frr-reset {
      type uint32;
      description "number of frr resets";
    }
    leaf mi-num-frr-proto-events {
      type uint32;
      description "number of frr events received in proto thread";
    }
    leaf mi-num-frr-logs {
      type uint32;
      description "frr log size";
    }
  }

  grouping FIB-SH-ROUTE-DEL-TS {
    description "FIB SH ROUTE DEL TS";
    leaf tableid {
      type uint32;
      description "tableid";
    }
    leaf prfx {
      type string {
        length "0..16";
      }
      description "prfx";
    }
    leaf prfx-len {
      type uint16;
      description "prfx len";
    }
    leaf prfx-proto {
      type uint16;
      description "prfx proto";
    }
    leaf msec-time {
      type uint64;
      description "msec time";
    }
  }

  grouping FIB-SH-PROTO-PURGE-STATS {
    description "FIB per protocol purge counters";
    list fpp-cntr {
      max-elements "3";

      description "the number of frees for this proto";
        leaf entry {
                  type uint32;
        }
    }
  }

  grouping FIB-SH-GTRIE-FN-TIMING {
    description
      "FIB timing statistics for individual gtrie
      functions";
    leaf fgft-fn {
      type string {
        length "0..64";
      }
      description "Gtrie operation";
    }
    leaf fgft-tot-updates {
      type uint64;
      description "Total number of updates";
    }
    leaf fgft-tot-updates-zero {
      type uint64;
      description
        "Total number of updates with zero timing (due to
        timestamp granularity)";
    }
    leaf fgft-tot-upd-time {
      type uint64;
      description "Total time for updates";
    }
    leaf fgft-max-time {
      type uint64;
      description "Time for the update";
    }
    leaf fgft-max-tstamp {
      type uint64;
      description "Time stamp of max update";
    }
  }

  grouping FIB-SH-GTRIE-TIMING {
    description "FIB platform update statistics";
    leaf fgt-num-success {
      type uint64;
      description "Number of successful updates";
    }
    leaf fgt-num-failure {
      type uint64;
      description "Number of unsuccessful updates";
    }
    leaf fgt-upd-total-time {
      type uint64;
      description "Total time for all pd updates";
    }

    list fgt-gtrie-fn-timing {
      description
        "Array of max time info indexed by gtrie function";
      uses FIB-SH-GTRIE-FN-TIMING;
    }
  }

  grouping FIB-SH-OBJ-ACTION-STATS {
    description
      "FIB Max time statistics for each action types of
      an object";
    leaf foas-tot-updates {
      type uint64;
      description "Total number of updates";
    }
    leaf foas-tot-upd-time {
      type uint64;
      description "Total time for updates";
    }
    leaf foas-tot-updates-zero {
      type uint64;
      description "Total number of updates that took zero time";
    }
    leaf foas-num-success {
      type uint64;
      description "Total number of successful updates";
    }
    leaf foas-num-failure {
      type uint64;
      description "Total number of failed updates";
    }
    leaf foas-max-time {
      type uint64;
      description "Time for the update";
    }
    leaf foas-max-tstamp {
      type uint64;
      description "Time stamp of max update";
    }
  }

  grouping FIB-SH-OBJ-STATS {
    description "FIB Max time statistics for each FIB object";
    leaf fos-tot-updates {
      type uint64;
      description "Total number of updates";
    }
    leaf fos-tot-upd-time {
      type uint64;
      description "Total time for updates";
    }

    list fos-obj-act-stat {
      description "Array of max time info indexed by action type";
      uses FIB-SH-OBJ-ACTION-STATS;
    }
  }

  grouping FIB-SH-PLATF-UPD-STATS {
    description "FIB platform update statistics";
    leaf fpus-num-success {
      type uint64;
      description "Number of successful updates";
    }
    leaf fpus-num-failure {
      type uint64;
      description "Number of unsuccessful updates";
    }
    leaf fpus-upd-total-time {
      type uint64;
      description "Total time for all pd updates";
    }

    list fpus-obj-stat {
      description "Array of max time info indexed by object type";
      uses FIB-SH-OBJ-STATS;
    }
  }

  grouping FIB-SH-PROTO-DEBUG-STATS {
    description "FIB per protocol debug information";

    container fpd-platf-upd-stats {
      description "platform update statistics";
      uses FIB-SH-PLATF-UPD-STATS;
    }

    container fpd-gtrie-timing {
      description "Gtrie timing statistics";
      uses FIB-SH-GTRIE-TIMING;
    }
    leaf fpd-gbltbl-entries {
      type uint64;
      description "the number of fib entries in global tbl";
    }
    leaf fpd-gbltbl-rej-entries {
      type uint64;
      description "the number of fib entries in global retry tbl";
    }
    leaf fpd-vrftbl-entries {
      type uint64;
      description "the number of fib entries in vrf tbls";
    }
    leaf fpd-vrftbl-rej-entries {
      type uint64;
      description "the number of fib entries in vrf retry tbls";
    }
    leaf fpd-num-tbls {
      type uint32;
      description "the number of tables in table set";
    }
    leaf fpd-bcdl-msgs {
      type uint64;
      description "the number of bcdl msgs";
    }
    leaf fpd-route-upd {
      type uint64;
      description "the number of route updates";
    }
    leaf fpd-route-del {
      type uint64;
      description "the number of route deletes";
    }
    leaf fpd-route-rcv {
      type uint64;
      description "the number of routes received";
    }
    leaf fpd-route-drops {
      type uint64;
      description "the number of routes dropped";
    }
    leaf fpd-lbl-recycled {
      type uint64;
      description
        "the number of routes handled with recycled label";
    }
    leaf fpd-version-mismatch-drops {
      type uint64;
      description
        "the number of routes dropped because of version
        mismatch";
    }
    leaf fpd-adj-upd {
      type uint64;
      description "the number of adjacency updates";
    }
    leaf fpd-adj-del {
      type uint64;
      description "the number of adjacency deletes";
    }
    leaf fpd-adj-upd-tx {
      type uint64;
      description "number of TX adjacency updates from AIB";
    }
    leaf fpd-adj-upd-tx-nh-found {
      type uint64;
      description
        "number of TX adjacency updates that found or
        created NH";
    }
    leaf fpd-adj-upd-tx-retry-created {
      type uint64;
      description
        "number of TX adjacency updates that went to
        retry";
    }
    leaf fpd-adj-tx-retry-nh-found {
      type uint64;
      description
        "number of TX adj retries that found or created
        NH";
    }
    leaf fpd-adj-tx-retry-obj-reinit {
      type uint64;
      description "number of times TX NH retry objects updated";
    }
    leaf fpd-adj-drops {
      type uint64;
      description " number of adj updates dropped because of OOR";
    }
    leaf fpd-adj-msg {
      type uint64;
      description "number of AIB messages";
    }
    leaf fpd-te-rcv {
      type uint64;
      description "the number of TE upds received";
    }
    leaf fpd-te-version-mismatch-drops {
      type uint64;
      description
        "the number of TE upds dropped because of version
        mismatch";
    }
    leaf fpd-num-retry-touts {
      type uint64;
      description "the number of retry timeouts";
    }
    leaf fpd-ldi-num-fixedup {
      type uint64;
      description "the number of fixup LDIs";
    }
    leaf fpd-ldi-num-correct-fixup {
      type uint64;
      description "the number of corrected fixup LDIs";
    }
    leaf fpd-pl-num-queued-fixedup {
      type uint64;
      description "the number of PL queued for fixup";
    }
    leaf fpd-pl-num-correct-fixup {
      type uint64;
      description "the number of corrected fixup PLs";
    }
    leaf fpd-pl-retry-add-exist {
      type uint64;
      description
        "the number PLs added to retry while already in
        retry";
    }
    leaf fpd-pl-inline-res-q {
      type uint64;
      description
        "the number of PLs linked to resolving tables for
        inline res";
    }
    leaf fpd-pl-with-backup-create-count {
      type uint64;
      description "number of pl creates with backu path";
    }
    leaf fpd-pl-with-backup-del-count {
      type uint64;
      description "number of pl deletes with backup path";
    }
    leaf fpd-pl-backup-enable-count {
      type uint64;
      description "number of PLs marked to include backup path";
    }
    leaf fpd-pl-backup-disable-count {
      type uint64;
      description " number of PLs unmarked to include backup path";
    }
    leaf fpd-pl-fast-nfn-count {
      type uint64;
      description "number of PLs visited on fast notification";
    }
    leaf fpd-ldi-backup-activate-count {
      type uint64;
      description "number of ldi backup path activications";
    }
    leaf fpd-ldi-last-backup-activate-time {
      type uint64;
      description "ldi mod time for last backup activation";
    }
    leaf fpd-ldi-max-backup-activate-time {
      type uint64;
      description "max ldi mod time for backup activation";
    }
    leaf fpd-ldi-min-backup-activate-time {
      type uint64;
      description "min ldi mod time for backup activation";
    }
    leaf fpd-ldi-total-backup-activate-time {
      type uint64;
      description "total ldi mod time for backup activation";
    }
    leaf fpd-ldi-avg-backup-activate-time {
      type uint64;
      description "avg ldi mod time for backup activation";
    }
    leaf fpd-recursion-constraint-count {
      type uint64;
      description
        "number of resolution failures because of
        recursion constraint";
    }
    leaf fpd-ldi-num-del-refcnt {
      type uint64;
      description "the number of deleted with non-zero refcount";
    }
    leaf fpd-retryq-size {
      type uint32;
      description "the number of elements in retryq";
    }
    leaf fpd-num-allocs {
      type uint64;
      description "the number of allocs for this proto";
    }
    leaf fpd-num-frees {
      type uint64;
      description "the number of frees for this proto";
    }
    leaf fpd-retryq-timeout {
      type uint32;
      description "timeout value in msec";
    }
    leaf fpd-retryq-sched-time {
      type uint32;
      description "Scheduler time period in msec";
    }
    list fpd-gbltbl-src-entry {
      max-elements "14";

      description

        "Number of global routes from                    

        each route source";
        leaf entry {
                  type uint64;
        }
    }
    list fpd-vrftbl-src-entry {
      max-elements "14";

      description

        "Number of vrf routes from                       

        each route source";
        leaf entry {
                  type uint64;
        }
    }
    list fpd-num-retry {
      description "the number of retries of each type";
        leaf entry {
                  type uint64;
        }
    }
  }

  grouping FIB-SH-MISC {
    description "FIB miscellaneous info";

    container mi-issu-state {
      description "FIB ISSU state";
      uses FIB-ISSU-STATE;
    }

    container mi-plat-capabilities {
      description "FIB platform capabilities";
      uses FIB-SH-PLAT-CAPABILITIES;
    }
    leaf mi-pfi-ifh-upd {
      type uint64;
      description "number of pfi ifh create notif";
    }
    leaf mi-pfi-ifh-del {
      type uint64;
      description "number of pfi ifh delete notif";
    }
    leaf mi-pfi-ifh-stale {
      type uint64;
      description "number of stale ifh removed";
    }
    leaf mi-tot-plat-upd-time {
      type uint64;
      description "total platform update time";
    }
    leaf mi-tot-gtrie-time {
      type uint64;
      description "total time spent in gtrie operations";
    }
    leaf mi-tot-dnld-time {
      type uint64;
      description "total download time";
    }
    leaf mi-clock-time {
      type uint64;
      description "clock download time";
    }
    leaf mi-cpu-time {
      type uint64;
      description "CPU download time";
    }
    leaf mi-shm-reset-ts {
      type uint64;
      description "Last FIB shared memory reset time stamp";
    }
    leaf mi-idb-recycle-count {
      type uint32;
      description "Number of idbs that hit ifh recycle";
    }
    leaf mi-idb-recycle-cleanup-count {
      type uint32;
      description
        "Number of idb cleaned up after hitting ifh
        recycle";
    }
    leaf mi-num-mgmt-list {
      type uint32;
      description "Number of management interfaces";
    }
    leaf mi-num-virtual-ll-addresses-added {
      type uint32;
      description "mi num virtual ll addresses added";
    }
    leaf mi-num-virtual-ll-addresses-deleted {
      type uint32;
      description "mi num virtual ll addresses deleted";
    }
    leaf mi-num-virtual-ll-addresses-dropped {
      type uint32;
      description "mi num virtual ll addresses dropped";
    }
    leaf mi-num-virtual-ll-addresses-cached {
      type uint32;
      description "mi num virtual ll addresses cached";
    }
    leaf mi-cpuless-init {
      type boolean;
      description "cpuless node list init";
    }
    leaf mi-cpuless-count {
      type uint32;
      description "count of cpuless line cards";
    }
    leaf mi-prefer-aib-routes-over-rib-oper {
      type boolean;
      description
        "Prefer AIB routes over RIB/LSD operational state";
    }
    leaf mi-prefer-aib-routes-over-rib-cfg {
      type boolean;
      description "Prefer AIB routes over RIB/LSD configured state";
    }
    leaf mi-xpl-ldi-enabled {
      type boolean;
      description "XPL loadinfo is enabled";
    }
    leaf mi-frr-follow-bgp-pic {
      type boolean;
      description "fast-reroute follow BGP-PIC configured";
    }
    leaf mi-encap-sharing-disable {
      type boolean;
      description "MPLS encapsulation sharing disabled";
    }
    leaf mi-lba-hash-recover {
      type boolean;
      description "Consistent-hashing auto-recovery";
    }
    list mi-idb-ext-cleanup-failed-count {
      max-elements "3";

      description

        "Number of recycled idb extensions that failed

        cleanup";
        leaf entry {
                  type uint32;
        }
    }
    list mi-lrpf-stats-fail {
      max-elements "9";

      description "Per protocol Failure stats for label RPF";
        leaf entry {
                  type uint32;
        }
    }
    list mi-lrpf-stats-act {
      max-elements "24";

      description "Per protocol actions stats for label RPF";
        leaf entry {
                  type uint32;
        }
    }
    list mi-lrpf-num {
      max-elements "3";

      description "Per protocol number of label RPFs";
        leaf entry {
                  type uint32;
        }
    }
    list mi-idb-lsec-enabled-num {
      max-elements "3";

      description

        "Number of interfaces having label security

        enabled";
        leaf entry {
                  type uint32;
        }
    }
    list mi-num-lisp-eid {
      max-elements "3";

      description "number of LISP EID prefixes";
        leaf entry {
                  type uint32;
        }
    }
    list mi-num-lisp-valid-eid {
      max-elements "3";

      description

        "number of LISP EID prefixes eligible for

        forwarding";
        leaf entry {
                  type uint32;
        }
    }
    list mi-cpuless-node {
      max-elements "20";

      description "list of cpuless line cards";
        leaf entry {
                  type uint32;
        }
    }

    list mi-proto-dbg-stat {
      description "Per protocol debug stats";
      uses FIB-SH-PROTO-DEBUG-STATS;
    }

    list mi-idb-purge-cntr {
      max-elements "3";
      description
        "the number of counters used for purge counter
        stats";
      uses FIB-SH-PROTO-PURGE-STATS;
    }

    list mi-del {
      description "Timestamps of deleted routes";
      uses FIB-SH-ROUTE-DEL-TS;
    }

    list mi-frr-stat {
      max-elements "3";
      description "FRR statistics";
      uses FIB-SH-PROTO-FRR-STATS;
    }
  }

  grouping FIB-SH-TBL-EXT-CLIENT-SUM {
    description "FIB external client summary information";

    container ses-pl-sum {
      description "ECD pathlist summary";
      uses FIB-SH-TBL-EXT-PL-SUM;
    }
    leaf ses-client-name {
      type string;
      description "External client name";
    }
    leaf ses-feci-fib-proto {
      type uint32;
      description "Registration proto";
    }
    leaf ses-num-regs {
      type uint32;
      description "Number of registrations";
    }
    leaf ses-num-pending {
      type uint32;
      description "Number of pending notifs";
    }
    leaf ses-client-pulsed-time {
      type uint64;
      description "Client pulsed timestamp";
    }
    leaf ses-comp-id {
      type uint32;
      description "component-id of the client";
    }
    leaf ses-ecd-version {
      type uint32;
      description "ECD version";
    }
  }

  grouping FIB-SH-FRR-NHINFO {
    description "FIB per nhinfo information";
    leaf si-frrtype {
      type uint32;
      description "FRR-NHinfo Type";
    }
    leaf si-refcount {
      type uint32;
      description "refcount";
    }
    leaf si-flags {
      type uint32;
      description "frr nhinfo flags";
    }
    leaf si-ifh {
      type uint32;
      description "ifh assoc w frr nh";
    }
    leaf si-main-ifh {
      type uint32;
      description "main ifh assoc w prot-frr nh";
    }
    leaf si-linktype {
      type uint32;
      description "Linktype using this FRR object";
    }
    leaf si-nh-pfx-proto {
      type uint32;
      description "Protocol for next-hop prefix";
    }
    leaf si-nh-pfx {
      type yang:hex-string;
      description "nh prefix";
    }
    leaf si-nh-pfx-len {
      type uint32;
      description "prefix len";
    }
    leaf si-tunid {
      type uint32;
      description "tunnel id for c12k";
    }
    leaf si-frr-ptr {
      type uint32;
      description "frr-nhinfo pointer";
    }
    leaf si-prot-frr-ptr {
      type uint32;
      description "prot-frr-nhinfo pointer for a bkup-frr";
    }
    leaf si-parent-nh-ptr {
      type uint32;
      description "parent nhinfo pointer";
    }
    leaf si-repl-parent-type {
      type uint8;
      description "replicated parent nhinfo type";
    }
    leaf si-upd-ts {
      type uint64;
      description "update timestamp";
    }
  }

  grouping FIB-SH-NHID-ENTRY {
    description "FIB per NHID entry information";
    leaf nh-interface-name-xr {
      type xr:Interface-name;
      description "Next-hop interface";
    }
    leaf nh-address-xr {
      type string;
      description "Next-hop address";
    }
    leaf nh-protocol {
      type uint8;
      description "Next-hop address protocol, IPv4/IPv6";
    }
    leaf nh-link-type {
      type uint8;
      description "Payload linktype";
    }
    leaf nh-table-id {
      type uint32;
      description "Table-ID entry notified for";
    }
    leaf nh-id-xr {
      type uint32;
      description "NHID value";
    }
    leaf nh-id-application {
      type uint8;
      description "NHID application type";
    }
    leaf version {
      type uint64;
      description "RIB version";
    }
    leaf time-of-last-update-in-msec {
      type uint64;
      description "The time of last update in msec";
    }
    leaf encap-id {
      type uint64;
      description "ENCAP ID value";
    }
  }

  grouping FIB-SRV6-GBL-UPD-LOC {
    description "FIB SRv6 global locator";
    leaf name {
      type string;
      description "Locator name";
    }
    leaf prefix {
      type string;
      description "Locator prefix";
    }
    leaf locator {
      type string;
      description "Locator";
    }
  }

  grouping FIB-SRV6-GBL-UPD {
    description "FIB SRv6 global update";
    leaf srv6-enabled {
      type boolean;
      description "Is SRv6 enabled?";
    }
    leaf encap-source-address {
      type inet:ipv6-address;
      description "Encap Source Address";
    }
    leaf locator-count {
      type uint32;
      description "Locator Count";
    }

    list locator {
      description "Locator Array";
      uses FIB-SRV6-GBL-UPD-LOC;
    }
  }

  grouping EVT-HIST-ENTRY {
    description "Event history Entry";
    leaf evt-timestamp {
      type string;
      description "The timestamp of the event";
    }
    leaf evt-name {
      type string;
      description "Event name";
    }
    leaf evt-type {
      type uint8;
      description "Event type";
    }
    leaf evt-many {
      type boolean;
      description "Multiple instance flag";
    }
    leaf evt-sticky {
      type boolean;
      description "Sticky flag";
    }
    list evt-data {
      description "Optional data";
        leaf entry {
                  type uint32;
        }
    }
  }

  grouping EVT-HIST-INFO {
    description "Per object event history";
    leaf evt-class-name {
      type string;
      description "Class name string";
    }

    list evt-entry {
      description "Array of event entries";
      uses EVT-HIST-ENTRY;
    }
  }

  grouping FIB-SH-INT-INTERNAL {
    description "FIB per interface internal information";

    container fib-idb-hist {
      description "Event History for IDB";
      uses EVT-HIST-INFO;
    }

    container fib-srte-head-hist {
      description "Event History for Srtehead";
      uses EVT-HIST-INFO;
    }
  }

  grouping FIB-SH-INT-DET {
    description "FIB per interface detail information";
    leaf interface-mtu {
      type uint16;
      description "Interface Protocol MTU";
    }
    leaf forwarding-flag {
      type boolean;
      description "Forwarding enabled/disabled flag";
    }
    leaf rpf-configured-flag {
      type boolean;
      description "RPF configured flag";
    }
    leaf rpf-mode {
      type Fib-rpf-mode;
      description "RPF mode";
    }
    leaf default-route-with-rpf {
      type boolean;
      description "Allow default route with RPF";
    }
    leaf self-ping-with-rpf {
      type boolean;
      description "Allow selfping with RPF";
    }
    leaf bgp-pa-input-configured-flag {
      type boolean;
      description "BGP PA configured flag";
    }
    leaf source-bgp-pa-input-configured-flag {
      type boolean;
      description "src BGP PA configured flag";
    }
    leaf destination-bgp-pa-input-configured-flag {
      type boolean;
      description "dst BGP PA configured flag";
    }
    leaf bgp-pa-output-configured-flag {
      type boolean;
      description "BGP PA configured flag";
    }
    leaf source-bgp-pa-output-configured-flag {
      type boolean;
      description "src BGP PA configured flag";
    }
    leaf destination-bgp-pa-output-configured-flag {
      type boolean;
      description "dst BGP PA configured flag";
    }
    leaf icmp-flag {
      type uint32;
      description "ICMP  configured flag";
    }
    leaf multi-label-drop-flag {
      type boolean;
      description "Drop packets with multiple-label-stack if set";
    }
  }

  grouping FIB-SH-INT {
    description "FIB per interface information";

    container detail-fib-int-information {
      description "Detailed FIB interface information";
      uses FIB-SH-INT-DET;
    }

    container si-internal {
      description "Internal Information";
      uses FIB-SH-INT-INTERNAL;
    }
    leaf per-interface {
      type xr:Interface-name;
      description "Interface handle";
    }
    leaf fib-interface-type {
      type uint32;
      description "FIB Interface type";
    }
    leaf fib-id-pointer {
      type uint32;
      description "Pointer to fibidb";
    }
    leaf fib-id-flags {
      type uint32;
      description "Flags on fibidb";
    }
    leaf fib-id-extension-pointer {
      type uint32;
      description "Pointer to fibidb extension";
    }
    leaf fib-id-extension-flags {
      type uint32;
      description "Flags on fibidb extension";
    }
    leaf number-of-dependent-next-hop-information {
      type uint32;
      description "Number of dependent nhinfo's";
    }
    leaf vrf-local-cef-information-pointer {
      type uint32;
      description "Vrf local cef info ptr";
    }
    leaf reference-count {
      type uint16;
      description "Reference count";
    }
    leaf last-modified-time {
      type uint32;
      description "Time last modified";
    }
    leaf last-operation {
      type Fibidb-oper;
      description "Last Oper";
    }
    leaf protocol-enabled {
      type boolean;
      description "Is the protocol configured?";
    }
    leaf referance-count-for-protocol {
      type uint32;
      description "Reference count for the protocol";
    }
    leaf number-of-input-packets {
      type uint64;
      description "Number of input packets";
    }
    leaf number-of-input-bytes {
      type uint64;
      units "byte";
      description "Number of input bytes";
    }
    leaf number-of-output-packets {
      type uint64;
      description "Number of output packets";
    }
    leaf number-of-output-bytes {
      type uint64;
      units "byte";
      description "Number of output bytes";
    }
    leaf interface-up-flag {
      type boolean;
      description "Interface up flag";
    }
    leaf per-packet-load-balancing-flag {
      type boolean;
      description "Per packet loadbalancing flag";
    }
    leaf p2p-interface-flag {
      type boolean;
      description "P2P interface flag";
    }
    leaf loopback-interface-flag {
      type boolean;
      description "Loopback interface flag";
    }
    leaf null-interface-flag {
      type boolean;
      description "Null interface flag";
    }
    leaf tunnel-interface-flag {
      type boolean;
      description "Tunnel interface flag";
    }
    leaf gre-tunnel-interface-flag {
      type boolean;
      description "GRE Tunnel interface flag";
    }
    leaf punt-packets-from-fib-switching-flag {
      type boolean;
      description "Punt packets from FIB switching flag";
    }
    leaf drop-packets-while-fib-switching-flag {
      type boolean;
      description "Drop packets while FIB switching flag";
    }
    leaf punt-packets-from-linecard-flag {
      type boolean;
      description "Punt packets from linecard flag";
    }
    leaf primary-ipv4-address {
      type string {
        length "0..52";
      }
      description "Pimary local v4 address for the interface";
    }
    leaf primary-ipv6-address {
      type string {
        length "0..52";
      }
      description "Pimary local v6 address for the interface";
    }
  }

  grouping FIB-SH-TBL-FIB-EXT-DET {
    description "FIB entry extension list information";
    leaf context-label-flag {
      type boolean;
      description "Context Label Exist";
    }
    leaf context-label {
      type uint32;
      description "Context Label";
    }
  }

  grouping FIB-SH-TBL-FIB-EXT-CMN-DET {
    description "FIB SH TBL FIB EXT CMN DET";

    container sfecd-le {
      when "../type = 'leaf-extension'" {
        description "../type = 'LeafExtension'";
      }
      description "sfecd le";
      uses FIB-SH-TBL-FIB-EXT-DET;
    }
    leaf type {
      type Fib-sh-tbl-fib-ext-bag;
      description "type";
    }
  }

  grouping FIB-SH-TBL-MPLS-LABEL-STACK {
    description
      "mpls label stack information for FIB table
      entries";
    leaf number-of-labels {
      type uint32;
      description "NumberOfLabels";
    }
    leaf out-interface {
      type xr:Interface-name;
      description "OutInterface";
    }
    leaf nh-address {
      type string {
        length "0..52";
      }
      description "NHAddress";
    }
    list lstack {
      max-elements "23";

      description "lstack";
        leaf entry {
                  type uint32;
        }
    }
  }

  grouping FIB-SH-TBL-PATH-MPLS-INFO {
    description "mpls path information for FIB table entries";
    leaf local-lable {
      type uint32;
      description "LocalLable";
    }
    leaf recursive-fwd-chain {
      type boolean;
      description "RecursiveFwdChain";
    }
    leaf number-of-igp-paths {
      type uint32;
      description "NumberOfIGPPaths";
    }
    leaf remote-backup {
      type boolean;
      description "RemoteBackupPath";
    }
    list recursive-lbl-stack {
      description "Recursive Label(s)";
        leaf entry {
                  type uint32;
        }
    }

    list igp-label-stack-array {
      description "igp label stack array";
      uses FIB-SH-TBL-MPLS-LABEL-STACK;
    }
  }

  grouping FIB-SH-TBL-NNH-PATH {
    description "Detailed Next Next Hop Information";
    leaf next-next-hop-index {
      type uint8;
      description "Next next hop index";
    }
    leaf next-next-hop-prefix {
      type string {
        length "0..52";
      }
      description "Next next hop prefix";
    }
    leaf next-next-hop-interface {
      type uint32;
      description "Next next hop interface index";
    }
  }

  grouping FIB-SH-IPENCAP-HDR-DET {
    description "Detailed IP Encap Header Description";
    leaf ip-encap-hdr-type {
      type Fib-sh-ipencap-hdr;
      description "Header Type";
    }
    leaf ip-encap-hdrp {
      type yang:hex-string;
      description "Static Header";
    }
    leaf ip-encap-hdr-dyn {
      type uint32;
      description "Dynamic Header Fields";
    }
  }

  grouping FIB-SH-IPENCAP-DET {
    description "Detailed IP Encap Description";
    leaf ip-encap-hdr-count {
      type uint8;
      description "Header Count";
    }
    leaf ip-encap-locks {
      type uint32;
      description "IPEncap Object Locks";
    }
    leaf ip-encap-transport-tbl {
      type uint32;
      description "Transport Table";
    }
    leaf ipe-transport-vrf-name {
      type string;
      description "Transport VRF name";
    }
    leaf ip-encap-transport-af {
      type uint32;
      description "Transport AF";
    }
    leaf ip-encap-payload-af {
      type uint32;
      description "Payload AF";
    }
    leaf ip-encap-payload-mtu {
      type uint16;
      description "Payload MTU";
    }
    leaf ip-encap-parent {
      type uint32;
      description "Pointer to parent";
    }
    leaf ip-encap-parent-type {
      type uint32;
      description "Parent type enumeration";
    }

    list ip-encap-hdr {
      description "Headers";
      uses FIB-SH-IPENCAP-HDR-DET;
    }
  }

  grouping FIB-SH-TBL-PATH-DET {
    description "Detailed path information for FIB table entries";
    leaf ip-address-to-recurse {
      type string {
        length "0..52";
      }
      description "IP address to recurse to";
    }
    leaf label-to-recurse {
      type uint32;
      description "Local label to recurse over";
    }
    leaf detail-next-hop-prefix {
      type string {
        length "0..52";
      }
      description "Next hop prefix";
    }
    leaf next-hop-mask-length {
      type uint8;
      description "Next hop mask length";
    }
    leaf interface-associated-path {
      type xr:Interface-name;
      description "Interface associated with this path";
    }
    leaf next-hop-interface {
      type xr:Interface-name;
      description "Next hop interface";
    }
    leaf next-hop-vrf {
      type string {
        length "0..33";
      }
      description "Next hop VRF";
    }
    leaf tunnle-endpoint-id {
      type uint32;
      description "Tunnel endpoint id";
    }
    leaf lisprlocid {
      type uint32;
      description "LISP RLOC ID";
    }
    leaf number-of-dependencies-this-path {
      type uint32;
      description "No. of dependents for this path";
    }
    leaf robin-reset-value {
      type uint8;
      description "Round robin reset value";
    }
    leaf recurse-prefix-object {
      type boolean;
      description "Is recursion object a leaf?";
    }
    leaf next-prefix-recursion {
      type yang:hex-string;
      description "Next prefix recursion in the path";
    }
    leaf next-prefix-length {
      type uint8;
      description "Next prefix length";
    }
    leaf recurse-prefix-object2 {
      type boolean;
      description
        "Recursion has two leaves (e.g. implicit-null
        path)";
    }
    leaf next-prefix-recursion2 {
      type yang:hex-string;
      description "Next prefix2 recursion in the path";
    }
    leaf next-prefix-length2 {
      type uint8;
      description "Next prefix2 length";
    }
    leaf detail-fib-adjacency-type {
      type Fib-adjacency-show;
      description "FIB entry adjacency type";
    }
    leaf current-path-flag {
      type boolean;
      description "Current path flag";
    }
    leaf recursive-path-information {
      type boolean;
      description "Recursive path information is available";
    }
    leaf external-adjacency {
      type boolean;
      description "Path is an external adjacency";
    }
    leaf fib-path-nh-information-type {
      type Fib-neh;
      description "FIB Nhinfo type";
    }
    leaf fib-path-nh-information-type-special {
      type Fib-neh-special;
      description "FIB Nhinfo type special";
    }
    leaf weight-of-path {
      type uint32;
      description "Weight of the path";
    }
    leaf tunnel-class {
      type uint8;
      description "Tunnel class of the path";
    }
    leaf tunnel-is-forward-class {
      type boolean;
      description "Tunnel is forward class";
    }

    list spd-ipencap {
      description "IP Encap";
      uses FIB-SH-IPENCAP-DET;
    }

    list next-next-hop {
      description "Next Next hop sets";
      uses FIB-SH-TBL-NNH-PATH;
    }
  }

  grouping FIB-SH-TBL-PATH {
    description "Brief path information for FIB table entries";

    list fib-sh-tbl-path {
      description "fib sh tbl path";

      container more-detail-about-path {
        description "More detail about this path entry";
        uses FIB-SH-TBL-PATH-DET;
      }

      container mpls-information-for-path {
        description "mpls info for this path entry";
        uses FIB-SH-TBL-PATH-MPLS-INFO;
      }
      leaf hardware-information {
        type yang:hex-string;
        description "Hardware info";
      }
      leaf brief-interface-handle {
        type xr:Interface-name;
        description "Interface handle";
      }
      leaf brief-next-hop-prefix {
        type string {
          length "0..52";
        }
        description "Next hop prefix";
      }
      leaf via-label-to-recurse {
        type uint32;
        description "Local label to recurse over";
      }
      leaf brief-pnode-address {
        type string {
          length "0..52";
        }
        description "P-node address";
      }
      leaf brief-qnode-address {
        type string {
          length "0..52";
        }
        description "Q-node address";
      }
      leaf brief-lfa-protection-type {
        type Fib-update-path-lfa-protection;
        description "LFA protection type";
      }
      leaf resolved-path {
        type boolean;
        description "Resolved path";
      }
      leaf recursive-path {
        type boolean;
        description "Recursive path";
      }
      leaf packets-received-path {
        type boolean;
        description "Packets received on this path";
      }
      leaf attached-path {
        type boolean;
        description "Attached path";
      }
      leaf backup-path {
        type boolean;
        description "Backup path";
      }
      leaf best-external-path {
        type boolean;
        description "Best external path";
      }
      leaf protect-ignore {
        type boolean;
        description "Is protection ignored";
      }
      leaf path-dlb {
        type boolean;
        description "Is this the path used for DLB";
      }
      leaf path-flags {
        type uint32;
        description "Path flags";
      }
      leaf path-info-flags {
        type uint16;
        description "Path Info flags";
      }
      leaf path-index {
        type uint8;
        description "Path index";
      }
      leaf backup-index {
        type uint8;
        description "Backup path index";
      }
      leaf next-hop-index {
        type uint32;
        description "Next Hop Index";
      }
      leaf parent-interface-handle {
        type xr:Interface-name;
        description "Parent Interface Handle";
      }
      leaf recursionvia-len {
        type uint8;
        description "recursion via /N constraint";
      }
    }
  }

  grouping FIB-ADDR-STR {
    description "FIB address";
    leaf address {
      type string {
        length "0..60";
      }
      description "address";
    }
  }

  grouping FIB-SH-TBL-LOADINFO-INT {
    description
      "Internal load sharing information arrays for FIB
      table entries";
    leaf level-ofldis {
      type uint8;
      description "level of ldis";
    }
    leaf number-of-ldis {
      type uint8;
      description "no. of ldis";
    }
    leaf maximum-index-arrays {
      type uint32;
      description "Maximum index of the arrays";
    }
    leaf path-indices {
      type yang:hex-string;
      description "Path indices";
    }
    leaf path-ldi-numbers {
      type yang:hex-string;
      description "Path indices";
    }
    leaf maximum-slots {
      type uint32;
      description "Maximum slots";
    }
    leaf normalized-weights {
      type yang:hex-string;
      description "Normalized weights";
    }
    leaf tunnel-class-value {
      type yang:hex-string;
      description "Tunnel class value";
    }
    leaf is-pbts-info-valid {
      type boolean;
      description "PBTS info valid flag";
    }
    leaf pbts-class-offset {
      type yang:hex-string;
      description "PBTS class offset";
    }
    leaf pbts-class-num-paths {
      type yang:hex-string;
      description "PBTS class num paths";
    }
    leaf pbts-fallback-mapped-class {
      type yang:hex-string;
      description "PBTS class falls back to class";
    }
    leaf round-robin-disable {
      type boolean;
      description "Round Robin Disable";
    }
    leaf ldi-next-hop-buckets {
      type uint8;
      description "Number of LDI next hop buckets";
    }
    leaf platform-hardware-information {
      type yang:hex-string;
      description "Platform Hardware info";
    }
    list sanity-flag {
      description "Sanity flag";
        leaf entry {
                  type boolean;
        }
    }
    list interface-handle {
      description "Interface handle";
        leaf entry {
                  type xr:Interface-name;
        }
    }
    list weights-of-path {
      description "Weights of paths";
        leaf entry {
                  type uint32;
        }
    }

    list adjacency-address {
      description "Adjacency address";
      uses FIB-ADDR-STR;
    }

    list pbts-class-is-fallback-mapped {
      min-elements "9";
      max-elements "9";
      description "Does PBTS class fall back to drop or any class";
      leaf entry {
        type boolean;
        description "Array entry.";
      }
    }

    list pbts-fallback-to-drop {
      min-elements "9";
      max-elements "9";
      description "PBTS class falls back to drop";
      leaf entry {
        type boolean;
        description "Array entry.";
      }
    }

    list tunnel-is-forward-class {
      min-elements "128";
      max-elements "128";
      description "Tunnel is forward class";
      leaf entry {
        type boolean;
        description "Array entry.";
      }
    }
  }

  grouping FIB-SH-TBL-LOADINFO-DET {
    description
      "Detailed load sharing information for FIB table
      entries";

    container load-informtion-internal-data {
      description "Loadinfo internal data";
      uses FIB-SH-TBL-LOADINFO-INT;
    }
    leaf packets-through-load-information {
      type uint64;
      description "Packets through this loadinfo";
    }
    leaf bytes-through-load-information {
      type uint64;
      units "byte";
      description "Bytes through this loadinfo";
    }
    leaf total-packets-through-load-information {
      type uint64;
      description "Total packets through this loadinfo";
    }
    leaf total-bytes-through-load-information {
      type uint64;
      units "byte";
      description "Total bytes through this loadinfo";
    }
    leaf prefix-of-owner {
      type uint32;
      description "Prefix of the owner";
    }
    leaf mask-length-of-owner {
      type uint32;
      description "Mask length of the owner";
    }
    leaf load-information-reference-count {
      type uint16;
      description "Loadinfo reference count";
    }
    leaf per-dest-load-sharing-flag {
      type boolean;
      description "Per destination load sharing flag";
    }
    leaf load-information-owner-deleted-flag {
      type boolean;
      description "Loadinfo owner deleted flag";
    }
    leaf loadinfo-sanity-flag {
      type boolean;
      description "Loadinfo sanity flag";
    }
    leaf is-owner {
      type boolean;
      description "Owner flag";
    }
  }

  grouping FIB-SH-TBL-FIB-DET {
    description "Detailed FIB table entry information";

    container loadshare-information {
      description "Detailed Loadshare info";
      uses FIB-SH-TBL-LOADINFO-DET;
    }
    leaf fib-entry-version {
      type uint32;
      description "FIB entry version number";
    }
    leaf per-prefix-accounting {
      type uint8;
      description "Per Prefix Accounting";
    }
    leaf load-sharing-type {
      type Fib-loadshare-show;
      description "Load sharing type";
    }
    leaf fib-entry-adjacency-type {
      type Fib-adjacency-show;
      description "FIB entry adjacency type";
    }
    leaf fib-protocol-type {
      type uint32;
      description "FIB Protocol type";
    }
    leaf afi-fib-protocol-type {
      type uint32;
      description "AFI FIB protocol type";
    }
    leaf aib-l3-address {
      type yang:hex-string;
      description "AIB L3 Address";
    }
    leaf adjacency-address-length {
      type uint32;
      description "ADJ ADDR LEN";
    }
    leaf adjacency-interface {
      type uint32;
      description "ADJ IFH";
    }
    leaf fib-special-nh-information-type {
      type uint32;
      description "FIB Special NHINFO Type";
    }
    leaf fib-entry-adjacency-address {
      type yang:hex-string;
      description "FIB entry adj address";
    }
    leaf fib-entry-adjacency-interface {
      type uint32;
      description "FIB entry adjacency interface";
    }
    leaf packets-through-fib-entry {
      type uint64;
      description "Packets through this FIB entry";
    }
    leaf bytes-through-fib-entry {
      type uint64;
      units "byte";
      description "Bytes through this FIB entry";
    }
    leaf detailed-prefix-length {
      type uint32;
      description "Prefix length";
    }
    leaf prefix-protocol {
      type uint32;
      description "Prefix protocol";
    }
    leaf precedence-forpackets {
      type uint8;
      description "Precedence for packets to this entry";
    }
    leaf traffic-index-for-packets {
      type uint8;
      description "Traffic index for packets to this entry";
    }
    leaf switch-compontent-id {
      type uint32;
      description "Switch function compontent ID";
    }
    leaf fast-adjacency-flag {
      type boolean;
      description "Fast adjacency flag";
    }
    leaf illegal-fast-adjacency-flag {
      type boolean;
      description "Illegal fast adjacency flag";
    }
    leaf remote-adjacency-flag {
      type boolean;
      description "Remote adjacency flag";
    }
    leaf bgp-attribute-id {
      type uint32;
      description "BGP attribute id";
    }
    leaf bgp-local-attribute-id {
      type uint32;
      description "BGP local attribute id";
    }
    leaf bgp-attribute-origin-as {
      type uint32;
      description "BGP attribute origin as";
    }
    leaf bgp-attribute-next-hop-as {
      type uint32;
      description "BGP attribute next hop as";
    }
    leaf path-string {
      type yang:hex-string;
      description "As path string";
    }
    leaf extcom-string {
      type yang:hex-string;
      description "extcom st";
    }
    leaf com-string {
      type yang:hex-string;
      description "com st";
    }
    leaf extended-community {
      type uint32;
      description "extended community";
    }
    leaf qos-group {
      type uint32;
      description "qos group";
    }
    leaf mpls-fec {
      type uint32;
      description "mpls fec";
    }
    leaf qppb-qos-group-and-ip-precedence {
      type uint32;
      description "qppb QOS group and IP precedence";
    }
    leaf flow-tag {
      type uint8;
      description "PBR flow-tag";
    }
    leaf forward-class {
      type uint8;
      description "SPP forwarding class ID";
    }
    leaf pl-time-of-last-update-in-msec {
      type uint64;
      description "The time of last update for PL in msec";
    }
    leaf ldi-time-of-last-update-in-msec {
      type uint64;
      description "The time of last update for LDI in msec";
    }
    leaf lwldi-time-of-last-update-in-msec {
      type uint64;
      description "The time of last update for LW-LDI in msec";
    }
    leaf pl-time-stamp-type {
      type uint32;
      description "The type of time-stamp on PL";
    }
  }

  grouping FIB-SH-TBL-FIB {
    description "Basic FIB table information";

    container detail-fib-entry-information {
      description "Detailed FIB entry information";
      uses FIB-SH-TBL-FIB-DET;
    }

    container fib-entry-path {
      description "FIB entry path details";
      uses FIB-SH-TBL-PATH;
    }
    leaf protocol-type-fib-entry {
      type uint32;
      description "Proto type for this entry";
    }
    leaf platform-hardware {
      type yang:hex-string;
      description "Platform Hardware info";
    }
    leaf number-of-referances-to-path-list {
      type uint32;
      description "Number of references to the pathlist";
    }
    leaf path-list-flags {
      type uint32;
      description "The pathlist flags";
    }
    leaf path-list-source {
      type uint32;
      description "The pathlist source";
    }
    leaf number-of-referances-to-ldi {
      type uint32;
      description "Number of references to the LDI";
    }
    leaf ldi-flags {
      type uint32;
      description "The LDI flags";
    }
    leaf flags-external-ldi {
      type uint32;
      description "The flags of ext assocaited with LDI ";
    }
    leaf pointer-external-ldi {
      type uint32;
      description "The pointer to the ext assocaited with LDI";
    }
    leaf exact-path-interface-handle {
      type uint32;
      description "exact-path interface handle";
    }
    leaf exact-path-gre-interface-handle {
      type uint32;
      description "exact-path GRE physical interface handle";
    }
    leaf exact-route-gre-phys-ifh-avail {
      type boolean;
      description "exact-route GRE phy ifh available";
    }
    leaf exact-route-result {
      type boolean;
      description "exact-route result";
    }
    leaf prefix-is-static-or-connected {
      type boolean;
      description "Prefix is static or connected";
    }
    leaf packet-should-recieve {
      type boolean;
      description "Packet should always be received";
    }
    leaf prefix-connected {
      type boolean;
      description "Prefix is connected";
    }
    leaf prefix-for-adjancency {
      type boolean;
      description "Prefix is for an adjacency";
    }
    leaf prefix-for-pic-next-hop {
      type boolean;
      description "Prefix is for a PIC nexthop";
    }
    leaf purgable-after-purge-interval {
      type boolean;
      description "Purgable after the purge interval";
    }
    leaf broadcast-recive-flag {
      type boolean;
      description "Broadcast receive flag";
    }
    leaf broadcast-forward-flag {
      type boolean;
      description "Broadcast forward flag";
    }
    leaf zero-by-zero-route-as-default {
      type boolean;
      description "0/0 route added as default route";
    }
    leaf external-switch-triggered {
      type boolean;
      description "External switch function triggered";
    }
    leaf route-attribute-flag {
      type boolean;
      description "Route attributes summary flag";
    }
    leaf dummy-real-zero-route {
      type boolean;
      description "Dummy real zero route";
    }
    leaf ldi-lw-flag {
      type uint32;
      description "The LDI LW flags";
    }
    leaf ref-counter-of-ldi-lw-ldi {
      type uint32;
      description "The refcounter of LDI LW LDI";
    }
    leaf type-of-ldi-lw-ldi {
      type uint32;
      description "The type of LDI LW LDI";
    }
    leaf lspa-flags {
      type uint32;
      description "The LSPA flags";
    }
    leaf version-of-route {
      type uint64;
      description "The version of the route";
    }
    leaf fib-route-download-priority {
      type uint32;
      description "Priority at which the route was downloaded";
    }
    leaf time-of-last-update-in-msec {
      type uint64;
      description "The time of last update in msec";
    }
    leaf l2-subscriber-route {
      type boolean;
      description "Is L2 Subscriber route";
    }
    leaf l2-subscriber-xconnect-id {
      type uint32;
      description "XConnect-id associated with L2 subscriber";
    }
    leaf l2-subscriber-flags {
      type uint32;
      description "Flags associated with L2 subscriber";
    }
    leaf l2-subscriber-ip-protocol {
      type uint32;
      description "IP protocol associated with L2 subscriber";
    }
    leaf l2tpv3-cookie-length-bits {
      type uint32;
      description "L2TPv3 cookie length for L2 subscriber";
    }
    leaf route-for-external-reach-linecard-flag {
      type boolean;
      description
        "Route destined for Line Card that support
        External Reach only";
    }
    leaf route-source-not-preferred {
      type boolean;
      description
        "The source of this route is not preferred over
        other sources with the same prefix";
    }
    leaf route-is-sr-flag {
      type boolean;
      description "Route is a MPLS Segment-Routing prefix";
    }

    list extension-object {
      description "Leaf Extension Object List";
      uses FIB-SH-TBL-FIB-EXT-CMN-DET;
    }
  }

  grouping FIB-SH-NHINFO-EXT-REP-DET {
    description "NHINFO entry extension object information";
    leaf nh-info-replicated-type {
      type uint8;
      description "Replicated NHINFO type";
    }
    leaf nh-info-replicated-nh-id {
      type uint32;
      description "NHID of the replicated NHINFO";
    }
    leaf nh-info-replicated-encap-id {
      type uint64;
      description "ENCAP ID of the replicated NHINFO";
    }
    leaf nh-info-replicated-interface {
      type xr:Interface-name;
      description "Interface of the replicated NHINFO";
    }
  }

  grouping FIB-SH-NHINFO-EXT-CMN-DET {
    description "FIB SH NHINFO EXT CMN DET";

    container snecd-nhr {
      when "../type = 'replicated-nh-info'" {
        description "../type = 'ReplicatedNHINFO'";
      }
      description "snecd nhr";
      uses FIB-SH-NHINFO-EXT-REP-DET;
    }
    leaf type {
      type Fib-nhinfo-ext-bag;
      description "type";
    }
  }

  grouping FIB-SH-EXT-BASE {
    description "FIB object extension base information";

    container object-base {
      description "FIB Object Base information";
      uses FIB-SH-FIB-OBJ-BASE;
    }
    leaf parent-object-pointer {
      type uint64;
      description "FIB Extension Object's parent pointer";
    }
    leaf back-object-pointer {
      type uint64;
      description "FIB Extension Object's back pointer";
    }
  }

  grouping FIB-SH-NHINFO-EXT-DET {
    description "NHINFO entry extension internal information";

    container nh-info-extension-base {
      description "NHINFO Extension object base information";
      uses FIB-SH-EXT-BASE;
    }

    container nh-info-extension-detail {
      description "NHINFO Extension Detail Information";
      uses FIB-SH-NHINFO-EXT-CMN-DET;
    }
  }

  grouping FIB-SH-NHINFO-EXT {
    description "FIB per nhinfo info";

    list nh-info-extension-detail {
      description "NHINFO Extension Detail";
      uses FIB-SH-NHINFO-EXT-DET;
    }
  }

  grouping FIB-SH-NHINFO-PWHE-EXT {
    description "FIB PW-HE specific info";
    leaf pwhe-adjacency-client-data {
      type uint32;
      description "PW-HE specific client data in adjacency";
    }
    leaf vctype {
      type uint32;
      description "VC type";
    }
    leaf vc-internal-label {
      type uint32;
      description "VC Internal Label";
    }
    leaf cw-enabled {
      type boolean;
      description "Is CW enabled?";
    }
    leaf l2-overhead-bytes {
      type uint16;
      units "byte";
      description
        "L2 overhead bytes for interface stats accounting";
    }
    leaf dot1q-vlan-tag {
      type uint32;
      description "VLAN tag";
    }
  }

  grouping FIB-SH-NHINFO {
    description "FIB per nhinfo information";

    container si-pwhe {
      description "PW-HE interface extension";
      uses FIB-SH-NHINFO-PWHE-EXT;
    }

    container nh-info-extension {
      description "NHinfo Extensions";
      uses FIB-SH-NHINFO-EXT;
    }
    leaf si-link-proto {
      type uint32;
      description "FIB Protocol Type for NHINFO linktype";
    }
    leaf si-nhinfo {
      type uint32;
      description "NHinfo object";
    }
    leaf si-nhtype {
      type uint32;
      description "NHinfo Type";
    }
    leaf si-ifh {
      type uint32;
      description "Ifhndl assoc w nhinfo";
    }
    leaf si-pfi-interface-type {
      type uint32;
      description "Pamna Interface Type";
    }
    leaf si-adj-ptr {
      type uint32;
      description "Adj Ptr";
    }
    leaf si-adj-present {
      type boolean;
      description "nhinfo point to adj";
    }
    leaf si-special-type {
      type uint32;
      description "nature of special nhinfo";
    }
    leaf si-refcount {
      type uint32;
      description "refcount";
    }
    leaf si-flags {
      type uint32;
      description "nhinfo flags";
    }
    leaf si-adj-if {
      type uint32;
      description "ADJ Interface";
    }
    leaf si-ext-pfx {
      type yang:hex-string;
      description "Extension Prefix";
    }
    leaf si-ext-pfx-len {
      type uint32;
      description "Extension Prefix Len";
    }
    leaf si-ext-pfx-proto {
      type uint32;
      description "Extension Prefix Protocol";
    }
    leaf si-adj-address {
      type yang:hex-string;
      description "AIB L3 Address";
    }
    leaf si-adj-addrlen {
      type uint32;
      description "ADJ L3 address length";
    }
    leaf si-adj-addr-proto {
      type uint32;
      description "ADJ L3 address Protocol";
    }
    leaf si-adj-rw-len {
      type uint32;
      description "Length of Macstring";
    }
    leaf si-adj-rw {
      type yang:hex-string;
      description "Macstring for Adjacency";
    }
    leaf si-dep-nhinfo-type {
      type uint32;
      description "Depenedent nhinfo type";
    }
    leaf si-dep-nhinfo {
      type uint32;
      description "Dependent nhinfo";
    }
    leaf si-dep-nhinfo-ifh {
      type uint32;
      description "Dependent nhinfo ifhndl";
    }
    leaf si-bkup-frr {
      type uint32;
      description "pointer to Backup FRR obj";
    }
    leaf si-protect-frr {
      type uint32;
      description "pointer to protect FRR object";
    }
    leaf si-bkup-nhinfo {
      type uint32;
      description "Bacckup NHINFO obj";
    }
    leaf si-bkup-ifh {
      type uint32;
      description "Bacckup IFH";
    }
    leaf si-bkup-addr {
      type yang:hex-string;
      description "Bkup L3 Address";
    }
    leaf si-bkup-addrlen {
      type uint32;
      description "BKup L3 address length";
    }
    leaf si-bkup-addr-proto {
      type uint32;
      description "BKup L3 address Protocol";
    }
    leaf si-frr-active {
      type boolean;
      description "is FRR currently active";
    }
    leaf si-attr-is-ext-mgd {
      type boolean;
      description "NH is externally managed";
    }
    leaf si-attr-is-incomp {
      type boolean;
      description "NH is incomplete";
    }
    leaf si-attr-is-tunnel {
      type boolean;
      description "NH is assoc w a TE tunnel";
    }
    leaf si-attr-is-tunnel-srte {
      type boolean;
      description "NH is assoc w a SRTE tunnel";
    }
    leaf si-attr-is-gre-tunnel {
      type boolean;
      description "NH is assoc w a GRE tunnel";
    }
    leaf si-gre-ti {
      type uint32;
      description "GRE tunnel info";
    }
    leaf si-gre-ti-flags {
      type uint32;
      description "Flags on GRE tunnel info";
    }
    leaf si-gre-ti-refcnt {
      type uint32;
      description "Refcount on GRE tunnel info";
    }
    leaf si-gre-tos-propagate {
      type boolean;
      description "Is GRE TOS propagate set";
    }
    leaf si-hardware {
      type yang:hex-string;
      description "Platform Hardware info";
    }
    leaf si-nhinfo-ptr {
      type uint32;
      description "nhinfo pointer";
    }
    leaf si-fnb-idb-ptr {
      type uint32;
      description "pointer to idb";
    }
    leaf si-anc-ifh {
      type uint32;
      description "Ancestor IFH";
    }
    leaf si-gre-ti-resolving-leafp {
      type uint32;
      description "GRE resolving ip-leaf";
    }
    leaf si-gre-dest-addr {
      type yang:hex-string;
      description "GRE dest address";
    }
    leaf si-nhid {
      type uint32;
      description "NHID value in the TX NH";
    }
    leaf si-upd-ts {
      type uint64;
      description "NH update timestamp";
    }
  }

  grouping FIB-SH-TIMESPEC {
    description "FIB SH TIMESPEC";
    leaf seconds {
      type int32;
      description "Seconds";
    }
    leaf nano-seconds {
      type int32;
      description "NanoSeconds";
    }
  }

  grouping FIB-SH-FRR-LOG {
    description "FIB frr log information";

    container frr-timestamp {
      description "frr timestamp";
      uses FIB-SH-TIMESPEC;
    }
    leaf frr-protocol-type {
      type Fib-frr-protocol-show;
      description "FIB Protocol Type";
    }
    leaf frr-interface-name {
      type xr:Interface-name;
      description "Interface assoc w frr nh";
    }
    leaf frr-prefix {
      type string {
        length "0..52";
      }
      description "nh prefix";
    }
    leaf frr-switching-time {
      type uint32;
      description "frr switching time";
    }
    leaf bundle-member-interface-name {
      type xr:Interface-name;
      description "bundle member";
    }
  }

  grouping FIB-SH-TBL-EXT-PL-SUM {
    description "FIB external client pathlist summary";
    leaf sep-num-ecd-pathlist {
      type uint32;
      description "Number of ECD pathlists";
    }
    leaf sep-num-ecd-pl-unresolved {
      type uint32;
      description "Number of ECD pathlists unresolved";
    }
    list sep-num-ecd-pl-per-interest {
      max-elements "13";

      description "Number of ECD pathlists per interest";
        leaf entry {
                  type uint32;
        }
    }
  }

  grouping FIB-SH-TBL-EXT-SUM-ALL {
    description
      "FIB external brief summary information across all
      clients";

    container sesa-pl-sum {
      description "External pathlist summary";
      uses FIB-SH-TBL-EXT-PL-SUM;
    }
    leaf sesa-num-client {
      type uint32;
      description "Client information";
    }
  }

  grouping FIB-SH-PFX-MASKLEN-CNT {
    description "FIB Prefix Masklength counts";
    leaf mask-length {
      type uint8;
      description "Mask length";
    }
    leaf number-of-prefixes {
      type uint32;
      description "Number of prefixes with given mask length";
    }
  }

  grouping FIB-SH-PFX-MASKLEN-DISTRIB {
    description "FIB Prefix Masklengths distribution";

    list unicast-prefixe {
      description "Masklength counts for unicast prefixes";
      uses FIB-SH-PFX-MASKLEN-CNT;
    }

    list broadcast-prefixe {
      description "Masklength counts for broadcast prefixes";
      uses FIB-SH-PFX-MASKLEN-CNT;
    }

    list multicast-prefix {
      description "Masklength counts for multicast prefixes";
      uses FIB-SH-PFX-MASKLEN-CNT;
    }
  }

  grouping FIB-PL-LDI-COUNT {
    description "FIB Pathlist and Loadinfo summary";
    leaf total-load-sharing-element-bytes {
      type uint32;
      units "byte";
      description
        "Total memory used by load sharing elements in
        bytes";
    }
    leaf total-load-sharing-element-references {
      type uint64;
      description
        "Total count of references to load sharing
        elements";
    }
    leaf total-path-list-elements {
      type uint32;
      description "Total count of Pathlist elements";
    }
    leaf recursive-path-list-elements {
      type uint32;
      description "Count of recursive Pathlist elements";
    }
    leaf platform-shared-path-list-elements {
      type uint32;
      description "Count of platform shared Pathlist elements";
    }
    leaf retry-path-list-elements {
      type uint32;
      description "Count of Pathlist elements in retry";
    }
    leaf total-load-info-elements {
      type uint32;
      description "Total count of Loadinfo elements";
    }
    leaf recursive-load-info-elements {
      type uint32;
      description "Count of recursive Loadinfo elements";
    }
    leaf platform-shared-load-info-elements {
      type uint32;
      description "Count of platform shared Loadinfo elements";
    }
    leaf xpl-load-info-elements {
      type uint32;
      description "Count of XPL Loadinfo elements";
    }
  }

  grouping FIB-SH-SUM {
    description "FIB summary statistics";

    container exclusive-load-sharing-element {
      description "Exclusive load sharing element";
      uses FIB-PL-LDI-COUNT;
    }

    container shared-load-sharing-element {
      description "Shared load sharing element";
      uses FIB-PL-LDI-COUNT;
    }

    container cross-shared-load-sharing-element {
      description "Cross-table shared load sharing element";
      uses FIB-PL-LDI-COUNT;
    }

    container encap-shared-load-sharing-element {
      description "Encap-shared load sharing element";
      uses FIB-PL-LDI-COUNT;
    }

    container prefix-masklen-distribution {
      description "Distribution of prefix mask lengths";
      uses FIB-SH-PFX-MASKLEN-DISTRIB;
    }
    leaf prefix {
      type yang:hex-string;
      description "The router-id";
    }
    leaf ss-tbl-id {
      type uint32;
      description "Table Id";
    }
    leaf ss-tbl-id-ptr {
      type uint32;
      description "Table Id Ptr";
    }
    leaf ss-vrf-id {
      type uint32;
      description "Virtual routing forwarding instance Id";
    }
    leaf ss-vr-id {
      type uint32;
      description "Virtual router instance Id";
    }
    leaf load-balancing {
      type Ss-lba-state;
      description "LBA configuration state";
    }
    leaf forwarding-elements {
      type uint32;
      description
        "Number of forwarding elements linked to the
        table";
    }
    leaf routes {
      type uint32;
      description "Number of routes";
    }
    leaf prefix-in-place-modifications {
      type uint32;
      description "Number of inplace modifications";
    }
    leaf stale-prefix-deletes {
      type uint32;
      description "Number of deleted stale leafs";
    }
    leaf load-sharing-elements {
      type uint32;
      description "Count of load sharing elements";
    }
    leaf load-sharing-references {
      type uint64;
      description "Count of load sharing references";
    }
    leaf total-load-share-element-bytes {
      type uint32;
      description "Total memory used by load sharing elements";
    }
    leaf leaves-used-bytes {
      type uint32;
      description "Total memory used by leaves";
    }
    leaf reresolve-entries {
      type uint32;
      description "Number of reresolved entries";
    }
    leaf old-unresolve-entries {
      type uint32;
      description "Number of old unresolved entries";
    }
    leaf new-unresolve-entries {
      type uint32;
      description "Number of new unresolved entries";
    }
    leaf unresolve-entries {
      type uint32;
      description "Number of total unresolved entries";
    }
    leaf cef-route-drops {
      type uint32;
      description "Number of routes dropped by CEF";
    }
    leaf cef-version-mismatch-route-drops {
      type uint64;
      description
        "the number of routes dropped due to version
        mismatch";
    }
    leaf delete-cache-num-entries {
      type uint32;
      description "Number of entries in the route delete cache";
    }
    leaf existing-leaves-revisions {
      type uint32;
      description "Number of entries present on addition";
    }
    leaf fib-default-prefix {
      type uint32;
      description "Default prefix";
    }
    leaf fib-default-prefix-mask-length {
      type uint32;
      description "Default prefix mask length";
    }
    leaf next-hops {
      type uint32;
      description "Number of NHINFOS";
    }
    leaf incomplete-next-hops {
      type uint32;
      description "Number of incomplete NHINFOS";
    }
    leaf resolution-timer {
      type uint32;
      units "second";
      description "IP CEF resolution timer in seconds";
    }
    leaf slow-process-timer {
      type uint32;
      units "second";
      description "IP CEF slow processing time in seconds";
    }
    leaf max-resolution-timer {
      type uint32;
      units "second";
      description "IP CEF max resolution time in seconds";
    }
    leaf imposition-prefixes {
      type uint32;
      description "Number of prefixes with imposition LDI";
    }
    leaf extended-prefixes {
      type uint32;
      description "Number of prefixes with extended path-list";
    }
    leaf cefl-bl-recycled-routes {
      type uint32;
      description
        "Number of routes updates with recycled label
        handled";
    }
    leaf ldi-backwalks {
      type uint32;
      description "pd backwalks on LDI modify with backup path";
    }
    leaf ss-prot-route-count {
      type uint32;
      description "Number of routes with FRR protection";
    }
    leaf lisp-eid-prefixes {
      type uint32;
      description
        "Number of lisp eid prefixes associated with
        table";
    }
    leaf lisp-eid-valid-prefixes {
      type uint32;
      description
        "Number of lisp eid prefixes eligible for
        forwarding";
    }
    leaf lisp-rloc-objects {
      type uint32;
      description
        "Number of lisp rloc objects associated with
        table";
    }
    leaf number-of-sr-labels {
      type uint32;
      description "Number of SR labels";
    }
    leaf ss-vxlan-ltep-ifh {
      type xr:Interface-name;
      description "VXLAN local Interface handle";
    }
    leaf ss-drop-pl-count {
      type uint32;
      description "Number of dropped pathlists";
    }
  }

  grouping FIB-SH-RSRC-SHM {
    description "Shared memory availability";
    leaf srs-curr-mode {
      type uint32;
      description "OOR mode for this shared memory window";
    }
    leaf srs-avg-avail {
      type uint64;
      units "byte";
      description "Average number of bytes available";
    }
    leaf srs-max-avail {
      type uint64;
      units "byte";
      description "Maximum bytes available";
    }
  }

  grouping FIB-SH-RSRC-AVAIL-STATE {
    description "FIB resource availability state";
    leaf sr-curr-mode {
      type uint32;
      description "Current overall oor mode";
    }
    leaf sr-hwrsrc-info {
      type yang:hex-string;
      description "Opaque hardware rsrc state info";
    }
    leaf sr-shmwin-oor-count {
      type uint8;
      description "sr shmwin oor count";
    }
    leaf sr-hw-oor-count {
      type uint8;
      description "sr hw oor count";
    }
    leaf sr-in-oor-ts {
      type uint64;
      description "sr in oor ts";
    }
    leaf sr-out-oor-ts {
      type uint64;
      description "sr out oor ts";
    }
    list sr-hwrsrc-mode {
      description "Hardware resource mode";
        leaf entry {
                  type uint32;
        }
    }

    list sr-shm-state {
      description "Current status of shared memories";
      uses FIB-SH-RSRC-SHM;
    }
  }

  grouping FIB-ISSU-PROTO-STATE {
    description "FIB ISSU protocol state";
    leaf protocol-name {
      type string {
        length "0..6";
      }
      description "Protocol name";
    }
    leaf aib-eod-time-stamp {
      type string {
        length "0..33";
      }
      description "AIB EODTimeStamp";
    }
    leaf rsi-eod-valid {
      type boolean;
      description "RSI EOD expected/valid";
    }
    leaf rsi-eod-time-stamp {
      type string {
        length "0..33";
      }
      description "RSI EOD received timestamp";
    }
    leaf lsd-eod-valid {
      type boolean;
      description "LSD EOD expected/valid";
    }
    leaf lsd-eod-time-stamp {
      type string {
        length "0..33";
      }
      description "LSD EOD received timestamp";
    }
    leaf lmrib-eod-valid {
      type boolean;
      description "LMRIB EOD expected/valid";
    }
    leaf lmrib-eod-time-stamp {
      type string {
        length "0..33";
      }
      description "LMRIB EOD received timestamp";
    }
    leaf rib-info-valid {
      type boolean;
      description "RIB table info valid";
    }
    leaf bcdl-tables {
      type uint32;
      description "Number of BCDL tables";
    }
    leaf converged-tables {
      type uint32;
      description "Number of tables converged";
    }
    leaf rib-tables-converged-time-stamp {
      type string {
        length "0..33";
      }
      description "All RIB tables converged timestamp";
    }
    leaf protocol-eod-valid {
      type boolean;
      description "Protocol EOD expected/valid";
    }
    leaf protocol-eod-time-stamp {
      type string {
        length "0..33";
      }
      description "Protocol EOD sent timestamp";
    }
  }

  grouping FIB-ISSU-STATE {
    description "FIB ISSU state";
    leaf imdr-support {
      type boolean;
      description "IMDR supported";
    }
    leaf slc-support {
      type boolean;
      description "SLC supported";
    }
    leaf fis-issu-restart {
      type boolean;
      description "ISSU restart";
    }
    leaf imdr-eoc-implicit {
      type boolean;
      description "IMDR End-of-config implicit";
    }
    leaf slc-eoc-implicit {
      type boolean;
      description "SLC End-of-config implicit";
    }
    leaf eoc-received-imdr-time-stamp {
      type string {
        length "0..33";
      }
      description "End-of-config received from IMDR timestamp";
    }
    leaf eoc-received-slc-time-stamp {
      type string {
        length "0..33";
      }
      description "End-of-config received from SLC timestamp";
    }
    leaf eod-received-im-time-stamp {
      type string {
        length "0..33";
      }
      description "End-of-download received from IM timestamp";
    }
    leaf eod-sent-imdr-time-stamp {
      type string {
        length "0..33";
      }
      description "End-of-download send to IMDR timestamp";
    }
    leaf eod-sent-slc-time-stamp {
      type string {
        length "0..33";
      }
      description "End-of-download send to SLC timestamp";
    }
    leaf fis-issu-error-ts {
      type uint64;
      description "ISSU error sent to ISSUMGR timetstamp";
    }

    list fis-proto-state {
      max-elements "3";
      description "IMDR state for the protocols";
      uses FIB-ISSU-PROTO-STATE;
    }
  }

  grouping FIB-SH-FIB-OBJ-BASE {
    description "FIB object base information";
    leaf object-reference-count {
      type uint32;
      description "FIB Object Reference Count";
    }
    leaf object-flags {
      type uint32;
      description "FIB Object flags";
    }
    leaf object-type {
      type uint8;
      description "FIB Object type";
    }
    leaf object-time-stamp {
      type uint64;
      description "FIB Object TimeStamp in msec";
    }
    leaf object-pointer {
      type uint64;
      description "FIB Object pointer";
    }
  }
}
